DefaultMib DEFINITIONS ::= BEGIN

    IMPORTS
        OBJECT-GROUP            								 FROM SNMPv2-CONF
        enterprises, IpAddress, Integer32, Unsigned32, OBJECT-TYPE,
        MODULE-IDENTITY, TimeTicks, NOTIFICATION-TYPE           FROM SNMPv2-SMI
        IANAifType                               				 FROM IANAifType-MIB
        InetAddressType, InetAddress, InetAddressIPv6           FROM INET-ADDRESS-MIB
        MacAddress, PhysAddress, DisplayString, TruthValue,RowStatus      FROM SNMPv2-TC;


    --SMI TEXTUAL-CONVENTION
        --String              ::= TEXTUAL-CONVENTION
            --STATUS          current
            --DESCRIPTION     ""
            --SYNTAX          OCTET STRING

        --UInt32              ::= TEXTUAL-CONVENTION
            --STATUS          current
            --DESCRIPTION     ""
            --SYNTAX          Unsigned32

        --Int32               ::= TEXTUAL-CONVENTION
            --STATUS          current
            --DESCRIPTION     ""
            --SYNTAX          Integer32

        --UInt64              ::= TEXTUAL-CONVENTION
            --STATUS          current
            --DESCRIPTION     ""
            --SYNTAX          Counter64

    ----------------------------------------------------------------------------
    -- Node definitions
    ----------------------------------------------------------------------------
    gbcom 								OBJECT IDENTIFIER ::= {enterprises 28723}
    ----------------------------------------------------------------------------
    -- alarmObject
    ----------------------------------------------------------------------------
    alarmObject                             OBJECT IDENTIFIER ::= {gbcom 1}

        alarmSn                             OBJECT-TYPE SYNTAX DisplayString(SIZE (0..32))
                                            MAX-ACCESS  accessible-for-notify   STATUS current 
                                            DESCRIPTION "alarm sn"
                                            ::= {alarmObject 1}
        alarmNeName                         OBJECT-TYPE SYNTAX DisplayString(SIZE (0..32))
                                            MAX-ACCESS  accessible-for-notify   STATUS current 
                                            DESCRIPTION "alarm ne name"
                                            ::= {alarmObject 2}
        alarmLevel                          OBJECT-TYPE SYNTAX Unsigned32{critical(1),main(2),minor(3),normal(4),unknown(5)}
                                            MAX-ACCESS  accessible-for-notify   STATUS current 
                                            DESCRIPTION "alarm level"
                                            DEFVAL {1}
                                            ::= {alarmObject 3}
        alarmType                           OBJECT-TYPE SYNTAX Unsigned32{communication(1),environment(2),device(3),handle-fail(4),qos(5),other(6)}
                                            MAX-ACCESS  accessible-for-notify   STATUS current 
                                            DESCRIPTION "alarm type"
                                            DEFVAL {1}
                                            ::= {alarmObject 4}
        alarmReasonID                       OBJECT-TYPE SYNTAX Unsigned32
                                            MAX-ACCESS  accessible-for-notify   STATUS current 
                                            DESCRIPTION "alarm reason id"
                                            DEFVAL {0}
                                            ::= {alarmObject 5}
        alarmReason                         OBJECT-TYPE SYNTAX DisplayString(SIZE (0..32))
                                            MAX-ACCESS  accessible-for-notify   STATUS current 
                                            DESCRIPTION "alarm reason"
                                            ::= {alarmObject 6}
        alarmRaiseTime                      OBJECT-TYPE SYNTAX TimeTicks
                                            MAX-ACCESS  accessible-for-notify   STATUS current 
                                            DESCRIPTION "alarm raise time"
                                            ::= {alarmObject 7}
        alarmStatus                         OBJECT-TYPE SYNTAX Unsigned32{active(1),clear(2)}
                                            MAX-ACCESS  accessible-for-notify   STATUS current 
                                            DESCRIPTION "alarm status"
                                            DEFVAL {1}
                                            ::= {alarmObject 8}
        alarmTitle                          OBJECT-TYPE SYNTAX DisplayString(SIZE (0..64))
                                            MAX-ACCESS  accessible-for-notify   STATUS current 
                                            DESCRIPTION "alarm title"
                                            ::= {alarmObject 9}
        alarmInfo                           OBJECT-TYPE SYNTAX DisplayString(SIZE (0..64))
                                            MAX-ACCESS  accessible-for-notify   STATUS current 
                                            DESCRIPTION "alarm info"
                                            ::= {alarmObject 10}
        updateOid                           OBJECT-TYPE SYNTAX OBJECT IDENTIFIER
                                            MAX-ACCESS  accessible-for-notify   STATUS current 
                                            DESCRIPTION "update oid"
                                            ::= {alarmObject 11}
        oldValue                            OBJECT-TYPE SYNTAX DisplayString(SIZE (0..64))
                                            MAX-ACCESS  accessible-for-notify   STATUS current 
                                            DESCRIPTION "ole value"
                                            ::= {alarmObject 12}
        newValue                            OBJECT-TYPE SYNTAX DisplayString(SIZE (0..64))
                                            MAX-ACCESS  accessible-for-notify   STATUS current 
                                            DESCRIPTION "new value"
                                            ::= {alarmObject 13}
        oidType                             OBJECT-TYPE SYNTAX Unsigned32{scalar(1),table(2)}
                                            MAX-ACCESS  accessible-for-notify   STATUS current 
                                            DESCRIPTION "oid type"
                                            ::= {alarmObject 14}
                                                                                    
    ----------------------------------------------------------------------------
    -- apConfig
    ----------------------------------------------------------------------------
    apConfig                                OBJECT IDENTIFIER ::= {gbcom 11}
    ----------------------------------------------------------------------------
    -- apSysConfig
    ----------------------------------------------------------------------------
    apSysConfig                             OBJECT IDENTIFIER ::= {apConfig 1}
    ----------------------------------------------------------------------------
    -- apDevInfo
    ----------------------------------------------------------------------------
    apDevInfo                               OBJECT IDENTIFIER ::= {apSysConfig 1}
                                    
        sysMacAddress                       OBJECT-TYPE SYNTAX MacAddress
                                            MAX-ACCESS  read-only   STATUS current 
                                            DESCRIPTION "ap mac address"
                                            ::= {apDevInfo 1}
        sysUpTime                           OBJECT-TYPE SYNTAX TimeTicks    UNITS "10 ms"
                                            MAX-ACCESS  read-only   STATUS current 
                                            DESCRIPTION "ap up time,since ap start"
                                            ::= {apDevInfo 2}
        sysRegetPeriod						OBJECT-TYPE SYNTAX Integer32   UNITS "second"
                                            MAX-ACCESS  read-write   STATUS current 
                                            DESCRIPTION "snmp agent reget period"
                                            ::= {apDevInfo 3}
        sysIfSpeed							OBJECT-TYPE SYNTAX Integer32   UNITS "Mbps"
                                            MAX-ACCESS  read-only   STATUS current 
                                            DESCRIPTION "ap interface speed"
                                            ::= {apDevInfo 4}
        sysTrapSwitch                       OBJECT-TYPE SYNTAX Integer32{off(0), on(1)}
                                            MAX-ACCESS  read-write   STATUS current 
                                            DESCRIPTION "ap trap switch"
                                            ::= {apDevInfo 5}
        sysRestart                       	OBJECT-TYPE SYNTAX Integer32{normal(0), restart(1)}
                                            MAX-ACCESS  read-write   STATUS current 
                                            DESCRIPTION "restart ap"
                                            ::= {apDevInfo 6}
        sysTimeZone							OBJECT-TYPE SYNTAX Integer32{utc(0), china(1), taiwan(2)}
                                            MAX-ACCESS  read-write   STATUS current 
                                            DESCRIPTION "system time zone"
                                            ::= {apDevInfo 7}                                    
        sysTime								OBJECT-TYPE SYNTAX DisplayString
                                            MAX-ACCESS  read-write   STATUS current 
                                            DESCRIPTION "system time, format:%Y-%m-%d %H:%M:%S"
                                            ::= {apDevInfo 8}
        sysIpAddress                        OBJECT-TYPE SYNTAX IpAddress
                                            MAX-ACCESS  read-only   STATUS current 
                                            DESCRIPTION "ap main ip address"
                                            ::= {apDevInfo 9}
        sysManageState                      OBJECT-TYPE SYNTAX Integer32{offline(0), online(1)}
                                            MAX-ACCESS  read-write   STATUS current 
                                            DESCRIPTION "ap manage state, the cms set it"
                                            ::= {apDevInfo 10}
        modelId                             OBJECT-TYPE SYNTAX Integer32
                                            MAX-ACCESS  read-only   STATUS current 
                                            DESCRIPTION "ap model id"
                                            ::= {apDevInfo 11}
        modelName                        	OBJECT-TYPE SYNTAX DisplayString
                                            MAX-ACCESS  read-only   STATUS current 
                                            DESCRIPTION "ap model name"
                                            ::= {apDevInfo 12}
        sysModel                            OBJECT-TYPE SYNTAX DisplayString
                                            MAX-ACCESS  read-only   STATUS current 
                                            DESCRIPTION "ap model"
                                            ::= {apDevInfo 13}
        timeOutInterval                     OBJECT-TYPE SYNTAX Integer32 UNITS "second"
                                            MAX-ACCESS  read-write   STATUS current 
                                            DESCRIPTION "sac time out interval"
                                            ::= {apDevInfo 14}
        heartBeatPeriod                     OBJECT-TYPE SYNTAX Integer32 UNITS "second"
                                            MAX-ACCESS  read-write   STATUS current 
                                            DESCRIPTION "heart beat period"
                                            ::= {apDevInfo 15}
        devType                             OBJECT-TYPE SYNTAX Integer32{gateway(1), ap(2)}
                                            MAX-ACCESS  read-only   STATUS current 
                                            DESCRIPTION "dev type"
                                            ::= {apDevInfo 16}       
        sysName								OBJECT-TYPE SYNTAX DisplayString
                                            MAX-ACCESS  read-only   STATUS current 
                                            DESCRIPTION "ap name"
                                            ::= {apDevInfo 17}                                                                                                                                                     
        sysHotId							OBJECT-TYPE SYNTAX DisplayString
                                            MAX-ACCESS  read-only   STATUS current 
                                            DESCRIPTION "ap hot id"
                                            ::= {apDevInfo 18}
        runState							OBJECT-TYPE SYNTAX Integer32{fault(0), normal(1)}
                                            MAX-ACCESS  read-only   STATUS current 
                                            DESCRIPTION "ap run state"
                                            ::= {apDevInfo 19}
        authCode							OBJECT-TYPE SYNTAX DisplayString
                                            MAX-ACCESS  read-only   STATUS current 
                                            DESCRIPTION "ap auth id"
                                            ::= {apDevInfo 20}
        authState							OBJECT-TYPE SYNTAX Integer32{unauthorized(0), authorize(1)}
                                            MAX-ACCESS  read-write   STATUS current 
                                            DESCRIPTION "ap run state"
                                            ::= {apDevInfo 21}
        partner                             OBJECT-TYPE SYNTAX DisplayString
                                            MAX-ACCESS  read-write   STATUS current 
                                            DESCRIPTION " "
                                            ::= {apDevInfo 22}
        line								OBJECT-TYPE SYNTAX DisplayString
                                            MAX-ACCESS  read-only   STATUS current 
                                            DESCRIPTION " "
                                            ::= {apDevInfo 23}
        manufacture                         OBJECT-TYPE SYNTAX DisplayString
                                            MAX-ACCESS  read-only   STATUS current 
                                            DESCRIPTION " "
                                            ::= {apDevInfo 24}
        serialNumber                        OBJECT-TYPE SYNTAX DisplayString
                                            MAX-ACCESS  read-only   STATUS current 
                                            DESCRIPTION " "
                                            ::= {apDevInfo 25}
        configState                         OBJECT-TYPE SYNTAX Integer32{none(0), config(1)}
                                            MAX-ACCESS  read-only   STATUS current 
                                            DESCRIPTION " "
                                            ::= {apDevInfo 26}       
        sysApWorkMode                       OBJECT-TYPE SYNTAX Integer32{fit(0), fat(1)}
                                            MAX-ACCESS  read-write   STATUS current 
                                            DESCRIPTION " "
                                            ::= {apDevInfo 27}                                                                                            
    ----------------------------------------------------------------------------
    -- apSwInfo
    ----------------------------------------------------------------------------
    apSwInfo	                            OBJECT IDENTIFIER ::= {apSysConfig 2}

        currentVersion                      OBJECT-TYPE SYNTAX DisplayString
                                            MAX-ACCESS  read-only   STATUS current 
                                            DESCRIPTION "ap current software version"
                                            ::= {apSwInfo 1}
        targetVersion                       OBJECT-TYPE SYNTAX DisplayString
                                            MAX-ACCESS  read-only   STATUS current 
                                            DESCRIPTION "ap software update target version"
                                            ::= {apSwInfo 2}
        softwareVersion                     OBJECT-TYPE SYNTAX DisplayString
                                            MAX-ACCESS  read-only   STATUS current 
                                            DESCRIPTION "ap software version"
                                            ::= {apSwInfo 3}                
                                                        
    ----------------------------------------------------------------------------
    -- apHwInfo
    ----------------------------------------------------------------------------
	-- 1.3.6.1.4.1.172.10.132.1.1.1.3
	apHardwareInfo 							OBJECT IDENTIFIER ::= { apSysConfig 3 }

        cpuType                             OBJECT-TYPE SYNTAX DisplayString
                                            MAX-ACCESS  read-only   STATUS current 
                                            DESCRIPTION "ap cpu type"
                                            ::= {apHardwareInfo 1}
        memoryType                          OBJECT-TYPE SYNTAX DisplayString
                                            MAX-ACCESS  read-only   STATUS current 
                                            DESCRIPTION "ap memory type"
                                            ::= {apHardwareInfo 2}
        memorySize                          OBJECT-TYPE SYNTAX Unsigned32    UNITS "MB"
                                            MAX-ACCESS  read-only   STATUS current 
                                            DESCRIPTION "ap memory size"
                                            ::= {apHardwareInfo 3}
        diskSize                            OBJECT-TYPE SYNTAX Unsigned32    UNITS "MB"
                                            MAX-ACCESS  read-only   STATUS current 
                                            DESCRIPTION "ap disk size"
                                            ::= {apHardwareInfo 4}
        hardwareVersion                     OBJECT-TYPE SYNTAX DisplayString
                                            MAX-ACCESS  read-only   STATUS current 
                                            DESCRIPTION "ap hardware version"
                                            ::= {apHardwareInfo 5}
        hardwareType                        OBJECT-TYPE SYNTAX Unsigned32{ap93(1),ta98(4),ta40(5),ta55(8) }
                                            MAX-ACCESS  read-only   STATUS current 
                                            DESCRIPTION "ap hardware type"
                                            ::= {apHardwareInfo 6}
        boardVersion                        OBJECT-TYPE SYNTAX Unsigned32
                                            MAX-ACCESS  read-only   STATUS current 
                                            DESCRIPTION "ap board version"
                                            ::= {apHardwareInfo 7}
        cpuInfo                             OBJECT-TYPE SYNTAX DisplayString
                                            MAX-ACCESS  read-only   STATUS current 
                                            DESCRIPTION " "
                                            ::= {apHardwareInfo 8}       
                                                                                             
    ----------------------------------------------------------------------------
    -- apIpConfig
    ----------------------------------------------------------------------------
    apIpConfig                      		OBJECT IDENTIFIER ::= {apSysConfig 4}   
    
    	ipNum								OBJECT-TYPE SYNTAX Unsigned32
                                            MAX-ACCESS  read-only   STATUS current 
                                            DESCRIPTION "ap ip num"
                                            ::= {apIpConfig 1}
    ----------------------------------------------------------------------------
    -- apIpConfigTable
    ----------------------------------------------------------------------------
    apIpConfigTable                  OBJECT-TYPE
        SYNTAX                  SEQUENCE OF ApIpConfigEntry
        MAX-ACCESS              not-accessible
        STATUS                  current
        DESCRIPTION             ""
        ::= {apIpConfig       10}

        apIpConfigEntry              OBJECT-TYPE
            SYNTAX                  ApIpConfigEntry
            MAX-ACCESS              not-accessible
            STATUS                  current
            DESCRIPTION             ""
            INDEX                   {ipIndex}
            ::= {apIpConfigTable      1}

        ApIpConfigEntry  ::= SEQUENCE
        {
            ipIndex        			Unsigned32,
            ipMode					Unsigned32,
            ipAddress               IpAddress,
            ipNetMask				IpAddress,
            ipGatewayAddress        IpAddress,
            ipDnsMaster				IpAddress,
            ipDnsSlave				IpAddress
        }

        ipIndex                          	OBJECT-TYPE SYNTAX Unsigned32
                                            MAX-ACCESS  read-only   STATUS current 
                                            DESCRIPTION "index"
                                            ::= {apIpConfigEntry 1}
        ipMode                              OBJECT-TYPE SYNTAX Unsigned32{static(0), dhcp(1), pppoe(2)}
                                            MAX-ACCESS  read-write   STATUS current 
                                            DESCRIPTION "ip mode"
                                            ::= {apIpConfigEntry 2}      
        ipAddress                           OBJECT-TYPE SYNTAX IpAddress
                                            MAX-ACCESS  read-write   STATUS current 
                                            DESCRIPTION "ip address"
                                            ::= {apIpConfigEntry 3}
        ipNetMask	                        OBJECT-TYPE SYNTAX IpAddress
                                            MAX-ACCESS  read-write   STATUS current 
                                            DESCRIPTION "ip net mask"
                                            ::= {apIpConfigEntry 4}
        ipGatewayAddress	                OBJECT-TYPE SYNTAX IpAddress
                                            MAX-ACCESS  read-write   STATUS current 
                                            DESCRIPTION "ip gateway address"
                                            ::= {apIpConfigEntry 5}                                    
        ipDnsMaster                         OBJECT-TYPE SYNTAX IpAddress
                                            MAX-ACCESS  read-write   STATUS current 
                                            DESCRIPTION "ip dns master"
                                            ::= {apIpConfigEntry 6}
        ipDnsSlave                          OBJECT-TYPE SYNTAX IpAddress
                                            MAX-ACCESS  read-write   STATUS current 
                                            DESCRIPTION "ip dns slave"
                                            ::= {apIpConfigEntry 7}
                                            
    ----------------------------------------------------------------------------
    -- apLegalApConfig
    ----------------------------------------------------------------------------
    apLegalApConfig                      	OBJECT IDENTIFIER ::= {apSysConfig 5}   
    
    	legalApNum							OBJECT-TYPE SYNTAX Unsigned32
                                            MAX-ACCESS  read-only   STATUS current 
                                            DESCRIPTION "legal ap num"
                                            ::= {apLegalApConfig 1}
    ----------------------------------------------------------------------------
    -- apLegalApConfigTable
    ----------------------------------------------------------------------------
    apLegalApConfigTable                  OBJECT-TYPE
        SYNTAX                  SEQUENCE OF ApLegalApConfigEntry
        MAX-ACCESS              not-accessible
        STATUS                  current
        DESCRIPTION             ""
        ::= {apLegalApConfig       10}

        apLegalApConfigEntry              OBJECT-TYPE
            SYNTAX                  ApLegalApConfigEntry
            MAX-ACCESS              not-accessible
            STATUS                  current
            DESCRIPTION             ""
            INDEX                   {legalApIndex}
            ::= {apLegalApConfigTable      1}

        ApLegalApConfigEntry  ::= SEQUENCE
        {
            legalApIndex        			Unsigned32,
            legalApSsid               		DisplayString,
            legalApBssid					MacAddress
        }

        legalApIndex                        OBJECT-TYPE SYNTAX Unsigned32
                                            MAX-ACCESS  read-create   STATUS current 
                                            DESCRIPTION "index"
                                            ::= {apLegalApConfigEntry 1}
        legalApSsid                         OBJECT-TYPE SYNTAX DisplayString
                                            MAX-ACCESS  read-only   STATUS current 
                                            DESCRIPTION "legal ap ssid"
                                            ::= {apLegalApConfigEntry 2}
        legalApBssid	                    OBJECT-TYPE SYNTAX MacAddress
                                            MAX-ACCESS  read-write   STATUS current 
                                            DESCRIPTION "legal ap bssid"
                                            ::= {apLegalApConfigEntry 3}

    ----------------------------------------------------------------------------
    -- apFlowConfig
    ----------------------------------------------------------------------------
    apFlowConfig                      	    OBJECT IDENTIFIER ::= {apSysConfig 6}   
    
    	apFlowSwitch						OBJECT-TYPE SYNTAX Integer32{off(0), on(1)}
                                            MAX-ACCESS  read-write   STATUS current 
                                            DESCRIPTION "ap flow switch"
                                            ::= {apFlowConfig 1}
        apUpLinkMaxRate						OBJECT-TYPE SYNTAX Integer32 UNITS"Kbps"
                                            MAX-ACCESS  read-write   STATUS current 
                                            DESCRIPTION "ap uplink max rate"
                                            ::= {apFlowConfig 2}                                    
        apDwLinkMaxRate						OBJECT-TYPE SYNTAX Integer32 UNITS"Kbps"
                                            MAX-ACCESS  read-write   STATUS current 
                                            DESCRIPTION "ap downlink max rate"
                                            ::= {apFlowConfig 3}
        staUpLinkMaxRate					OBJECT-TYPE SYNTAX Integer32 UNITS"Kbps"
                                            MAX-ACCESS  read-write   STATUS current 
                                            DESCRIPTION "sta uplink max rate"
                                            ::= {apFlowConfig 4}                                    
        staDwLinkMaxRate					OBJECT-TYPE SYNTAX Integer32 UNITS"Kbps"
                                            MAX-ACCESS  read-write   STATUS current 
                                            DESCRIPTION "sta downlink max rate"
                                            ::= {apFlowConfig 5}
                                                                                                                                                                                                                     
    ----------------------------------------------------------------------------
    -- apScanConfig
    ----------------------------------------------------------------------------
    apScanConfig	                        OBJECT IDENTIFIER ::= {apSysConfig 7}

        scanSwitch                      	OBJECT-TYPE SYNTAX Integer32{off(0),on(1)}
                                            MAX-ACCESS  read-write   STATUS current 
                                            DESCRIPTION "ap scan switch"
                                            ::= {apScanConfig 1}
        scanDegree                       	OBJECT-TYPE SYNTAX Integer32{high-precision(1),low-precision(2),pure-probe(3)}
                                            MAX-ACCESS  read-write   STATUS current 
                                            DESCRIPTION "ap scanning accuracy"
                                            ::= {apScanConfig 2}
                                                                                                                                                                                                                                                                                              
    ----------------------------------------------------------------------------
    -- apAdvanceConfig
    ----------------------------------------------------------------------------
    apAdvanceConfig                         OBJECT IDENTIFIER ::= {apConfig 2}                                            
    ----------------------------------------------------------------------------
    -- ap5GPriorConfig
    ----------------------------------------------------------------------------
    ap5GPriorConfig                         OBJECT IDENTIFIER ::= {apAdvanceConfig 1}

        ap5GPriorSwitch                     OBJECT-TYPE SYNTAX Integer32{off(0), on(1)}
                                            MAX-ACCESS  read-write   STATUS current 
                                            DESCRIPTION "ap 5G prior switch"
                                            ::= {ap5GPriorConfig 1}
        ap2dot4GDelayTime   				OBJECT-TYPE SYNTAX Integer32 UNITS "second"
                                            MAX-ACCESS  read-write   STATUS current 
                                            DESCRIPTION "ap 2.4G delay time"
                                            ::= {ap5GPriorConfig 2}                                    
        apStaTimeOut                        OBJECT-TYPE SYNTAX Integer32 UNITS "second"
                                            MAX-ACCESS  read-write   STATUS current 
                                            DESCRIPTION "ap station time out"
                                            ::= {ap5GPriorConfig 3}
    ----------------------------------------------------------------------------
    -- ap11nPriorConfig
    ----------------------------------------------------------------------------
    ap11nPriorConfig                        OBJECT IDENTIFIER ::= {apAdvanceConfig 2}

        ap11nPriorSwitch                    OBJECT-TYPE SYNTAX Integer32{off(0), on(1)}
                                            MAX-ACCESS  read-write   STATUS current 
                                            DESCRIPTION "ap 11n prior switch"
                                            ::= {ap11nPriorConfig 1}
        ap11bgDelayTime   					OBJECT-TYPE SYNTAX Integer32 UNITS "second"
                                            MAX-ACCESS  read-write   STATUS current 
                                            DESCRIPTION "ap 11bg delay time"
                                            ::= {ap11nPriorConfig 2}                                    
        ap11nPriorStaTimeOut                OBJECT-TYPE SYNTAX Integer32 UNITS "second"
                                            MAX-ACCESS  read-write   STATUS current 
                                            DESCRIPTION "ap station time out"
                                            ::= {ap11nPriorConfig 3}                                                                                         

    ----------------------------------------------------------------------------
    -- apRadioConfig
    ----------------------------------------------------------------------------
	apRadioConfig							OBJECT IDENTIFIER ::= {apConfig 3}
    ----------------------------------------------------------------------------
    -- apRadioConfigTable
    ----------------------------------------------------------------------------
    apRadioConfigTable                  OBJECT-TYPE
        SYNTAX                  SEQUENCE OF ApRadioConfigEntry
        MAX-ACCESS              not-accessible
        STATUS                  current
        DESCRIPTION             ""
        ::= {apRadioConfig       10}

        apRadioConfigEntry              OBJECT-TYPE
            SYNTAX                  ApRadioConfigEntry
            MAX-ACCESS              not-accessible
            STATUS                  current
            DESCRIPTION             ""
            INDEX                   {radioId}
            ::= {apRadioConfigTable      1}

        ApRadioConfigEntry  ::= SEQUENCE
        {
            radioId        			Integer32,
            radioMode				Integer32,
            bandWidth               Integer32,
            channel					Integer32,
            radioPower        		Integer32,
            lowRssi					Integer32
        }

        radioId                          	OBJECT-TYPE SYNTAX Integer32
                                            MAX-ACCESS  read-only   STATUS current 
                                            DESCRIPTION "radio id"
                                            ::= {apRadioConfigEntry 1}
        radioMode                           OBJECT-TYPE SYNTAX Integer32{a(1),b(2),g(3),b-g(6),an(8),a-an(9),gn(16),g-gn(20),b-g-gn(22)}
                                            MAX-ACCESS  read-write   STATUS current 
                                            DESCRIPTION "radio mode"
                                            ::= {apRadioConfigEntry 2}      
        bandWidth                           OBJECT-TYPE SYNTAX Integer32{bw20MHz-only(0), bw20MHz-40MHz-auto(1), bw40MHz-only(2)}
                                            MAX-ACCESS  read-write   STATUS current 
                                            DESCRIPTION "band width"
                                            ::= {apRadioConfigEntry 3}
        channel	                        	OBJECT-TYPE SYNTAX Integer32
                                            MAX-ACCESS  read-write   STATUS current 
                                            DESCRIPTION "channel"
                                            ::= {apRadioConfigEntry 4}
        radioPower	                		OBJECT-TYPE SYNTAX Integer32 UNITS "mw"
                                            MAX-ACCESS  read-write   STATUS current 
                                            DESCRIPTION "radio power"
                                            ::= {apRadioConfigEntry 5}                                    
        lowRssi                         	OBJECT-TYPE SYNTAX Integer32 UNITS "dbm"
                                            MAX-ACCESS  read-write   STATUS current 
                                            DESCRIPTION "user min power "
                                            ::= {apRadioConfigEntry 6}
 
    ----------------------------------------------------------------------------
    -- apSsidInfoConfig
    ---------------------------------------------------------------------------- 
	apSsidInfoConfig						OBJECT IDENTIFIER ::= {apConfig 4}
    ----------------------------------------------------------------------------
    -- apSsidInfoConfigTable
    ----------------------------------------------------------------------------
    apSsidInfoConfigTable                  OBJECT-TYPE
        SYNTAX                  SEQUENCE OF ApSsidInfoConfigEntry
        MAX-ACCESS              not-accessible
        STATUS                  current
        DESCRIPTION             ""
        ::= {apSsidInfoConfig       10}

        apSsidInfoConfigEntry              OBJECT-TYPE
            SYNTAX                  ApSsidInfoConfigEntry
            MAX-ACCESS              not-accessible
            STATUS                  current
            DESCRIPTION             ""
            INDEX                   {ssidIndex}
            ::= {apSsidInfoConfigTable      1}

        ApSsidInfoConfigEntry  ::= SEQUENCE
        {
            ssidIndex        			Integer32,
            wifiId						Integer32,
            vapId               		Integer32,
            vapName						DisplayString,
            ssid        				DisplayString,
            default						Integer32,
            encrypt                     Integer32,
            algorithm                   Integer32,
            key                         DisplayString,
            forwardMode                 Integer32,
            upRate                      Integer32,
            downRate                    Integer32,
            portalUrl                   DisplayString,
            onlineCtrlTime              Integer32,
            flowOffTime                 Integer32,
            rowStatus                   RowStatus
        }

        ssidIndex                          	OBJECT-TYPE SYNTAX Integer32
                                            MAX-ACCESS  read-only   STATUS current 
                                            DESCRIPTION ""
                                            ::= {apSsidInfoConfigEntry 1}
        wifiId                           	OBJECT-TYPE SYNTAX Integer32
                                            MAX-ACCESS  read-only   STATUS current 
                                            DESCRIPTION ""
                                            ::= {apSsidInfoConfigEntry 2}      
        vapId                           	OBJECT-TYPE SYNTAX Integer32
                                            MAX-ACCESS  read-only   STATUS current 
                                            DESCRIPTION ""
                                            ::= {apSsidInfoConfigEntry 3}
        vapName	                        	OBJECT-TYPE SYNTAX DisplayString
                                            MAX-ACCESS  read-only   STATUS current 
                                            DESCRIPTION ""
                                            ::= {apSsidInfoConfigEntry 4}
        ssid	                			OBJECT-TYPE SYNTAX DisplayString
                                            MAX-ACCESS  read-write   STATUS current 
                                            DESCRIPTION "r"
                                            ::= {apSsidInfoConfigEntry 5}                                    
        default                         	OBJECT-TYPE SYNTAX Integer32{non-default(0),default(1)}
                                            MAX-ACCESS  read-write   STATUS current 
                                            DESCRIPTION ""
                                            ::= {apSsidInfoConfigEntry 6}
        encrypt                             OBJECT-TYPE SYNTAX Integer32{open(0),wpa-psk-wpa2-psk(5)}
                                            MAX-ACCESS  read-write   STATUS current 
                                            DESCRIPTION ""
                                            ::= {apSsidInfoConfigEntry 7}
        algorithm                           OBJECT-TYPE SYNTAX Integer32{tkip(1),aes(2),aes-tkip(3)}
                                            MAX-ACCESS  read-write   STATUS current 
                                            DESCRIPTION ""
                                            ::= {apSsidInfoConfigEntry 8}
        key                                 OBJECT-TYPE SYNTAX DisplayString
                                            MAX-ACCESS  read-write   STATUS current 
                                            DESCRIPTION ""
                                            ::= {apSsidInfoConfigEntry 9}
        forwardMode                         OBJECT-TYPE SYNTAX Integer32{nat(1),bridge(2)}
                                            MAX-ACCESS  read-write   STATUS current 
                                            DESCRIPTION ""
                                            ::= {apSsidInfoConfigEntry 10}
        upRate                              OBJECT-TYPE SYNTAX Integer32 UNITS "KBps"
                                            MAX-ACCESS  read-write   STATUS current 
                                            DESCRIPTION ""
                                            ::= {apSsidInfoConfigEntry 11}
        downRate                            OBJECT-TYPE SYNTAX Integer32 UNITS "KBps"
                                            MAX-ACCESS  read-write   STATUS current 
                                            DESCRIPTION ""
                                            ::= {apSsidInfoConfigEntry 12}
        portalUrl                           OBJECT-TYPE SYNTAX DisplayString
                                            MAX-ACCESS  read-write   STATUS current 
                                            DESCRIPTION ""
                                            ::= {apSsidInfoConfigEntry 13}
        onlineCtrlTime                      OBJECT-TYPE SYNTAX Integer32 UNITS "minutes"
                                            MAX-ACCESS  read-write   STATUS current 
                                            DESCRIPTION ""
                                            ::= {apSsidInfoConfigEntry 14}
        flowOffTime                         OBJECT-TYPE SYNTAX Integer32 UNITS "minutes"
                                            MAX-ACCESS  read-write   STATUS current 
                                            DESCRIPTION ""
                                            ::= {apSsidInfoConfigEntry 15}
        rowStatus                           OBJECT-TYPE SYNTAX RowStatus{active(1),notInService(2),notReady(3),createAndGo(4),createAndWait(5),destroy(6)}
                                            MAX-ACCESS  read-write   STATUS current 
                                            DESCRIPTION ""
                                            ::= {apSsidInfoConfigEntry 16}
                                                                                                                                                              
    ----------------------------------------------------------------------------
    -- apWifiDeviceConfig
    ----------------------------------------------------------------------------
    apWifiDeviceConfig                      OBJECT IDENTIFIER ::= {apConfig 10}   

    ----------------------------------------------------------------------------
    -- apWifiDeviceBasicConfig
    ----------------------------------------------------------------------------
    apWifiDeviceBasicConfig                 OBJECT IDENTIFIER ::= {apWifiDeviceConfig 1}

        basicWifiId                         OBJECT-TYPE SYNTAX Integer32
                                            MAX-ACCESS  read-only   STATUS current 
                                            DESCRIPTION "2.4G wifi id"
                                            ::= {apWifiDeviceBasicConfig 1}
        wifiDeviceMac                       OBJECT-TYPE SYNTAX MacAddress
                                            MAX-ACCESS  read-only   STATUS current 
                                            DESCRIPTION "2.4G wifi mac address"
                                            ::= {apWifiDeviceBasicConfig 2}             
        wifiDeviceType                      OBJECT-TYPE SYNTAX Integer32{ap-single(0),ap-ms(1),adhoc-single(2),adhoc-ms(3),ap-adhoc(4),sta-adhoc(5),sta-single(6),sta-ms(7)}
                                            MAX-ACCESS  read-only   STATUS current 
                                            DESCRIPTION "2.4G wifi type"
                                            ::= {apWifiDeviceBasicConfig 3}
            
    ----------------------------------------------------------------------------
    -- apWifiDeviceChannelConfig
    ----------------------------------------------------------------------------
    apWifiDeviceChannelConfig               OBJECT IDENTIFIER ::= {apWifiDeviceConfig 2}

        channelWifiId                       OBJECT-TYPE SYNTAX Integer32
                                            MAX-ACCESS  read-only   STATUS current 
                                            DESCRIPTION "2.4G wifi id"
                                            ::= {apWifiDeviceChannelConfig 1}
        channelBGNMode                      OBJECT-TYPE SYNTAX Integer32{dot11b(2),dot11g(3),dot11bg(6),dot11n(16),dot11g-gn(20),dot11bgn(22)}
                                            MAX-ACCESS  read-write   STATUS current 
                                            DESCRIPTION "2.4G wifi channel abg mode"
                                            ::= {apWifiDeviceChannelConfig 2}
        channelUsing                     	OBJECT-TYPE SYNTAX Integer32
                                            MAX-ACCESS  read-only   STATUS current 
                                            DESCRIPTION "2.4G current wifi channel"
                                            ::= {apWifiDeviceChannelConfig 3}
        channelState                  		OBJECT-TYPE SYNTAX Integer32{static(0),auto(1)}
                                            MAX-ACCESS  read-write   STATUS current 
                                            DESCRIPTION "2.4G wifi channel type"
                                            ::= {apWifiDeviceChannelConfig 4}
        autoChanTime                		OBJECT-TYPE SYNTAX Integer32 UNITS "second"
                                            MAX-ACCESS  read-write   STATUS current 
                                            DESCRIPTION "2.4G wifi auto channel time"
                                            ::= {apWifiDeviceChannelConfig 5}
        staticChannel               		OBJECT-TYPE SYNTAX Integer32 
                                            MAX-ACCESS  read-write   STATUS current 
                                            DESCRIPTION "2.4G wifi static channel"
                                            ::= {apWifiDeviceChannelConfig 6}
        autoChanList                   		OBJECT-TYPE SYNTAX DisplayString
                                            MAX-ACCESS  read-write   STATUS current 
                                            DESCRIPTION "2.4G wifi channel list"
                                            ::= {apWifiDeviceChannelConfig 7}
        rfNum                               OBJECT-TYPE SYNTAX Integer32{one(1),two(2),three(3),four(4)}
                                            MAX-ACCESS  read-write   STATUS current 
                                            DESCRIPTION "2.4G rf num"
                                            ::= {apWifiDeviceChannelConfig 8}     
        bwMode                              OBJECT-TYPE SYNTAX Integer32{bw20MHz-only(0), bw20MHz-40MHz-auto(1), bw40Hz-only(2)}
                                            MAX-ACCESS  read-write   STATUS current 
                                            DESCRIPTION "2.4G bw mode"
                                            ::= {apWifiDeviceChannelConfig 9}     
                                    
    ----------------------------------------------------------------------------
    -- apWifiDevicePowerConfig
    ----------------------------------------------------------------------------
    apWifiDevicePowerConfig                 OBJECT IDENTIFIER ::= {apWifiDeviceConfig 3}

        powerWifiId                         OBJECT-TYPE SYNTAX Integer32
                                            MAX-ACCESS  read-only   STATUS current 
                                            DESCRIPTION "2.4G wifi id"
                                            ::= {apWifiDevicePowerConfig 1}
        maxTxPower                          OBJECT-TYPE SYNTAX Integer32    UNITS "dBm"
                                            MAX-ACCESS  read-only   STATUS current 
                                            DESCRIPTION "2.4G wifi max tx power"
                                            ::= {apWifiDevicePowerConfig 2}
        decayTxPower                        OBJECT-TYPE SYNTAX Integer32  UNITS "dB"
                                            MAX-ACCESS  read-write   STATUS current 
                                            DESCRIPTION "2.4G wifi decay tx power"
                                            ::= {apWifiDevicePowerConfig 3}
        transmitPower                       OBJECT-TYPE SYNTAX Integer32   UNITS "dB"
                                            MAX-ACCESS  read-only   STATUS current 
                                            DESCRIPTION "2.4G wifi transmit power"
                                            ::= {apWifiDevicePowerConfig 4}

    ----------------------------------------------------------------------------
    -- apWifiDeviceAdvanceConfig
    ----------------------------------------------------------------------------
    apWifiDeviceAdvanceConfig               OBJECT IDENTIFIER ::= {apWifiDeviceConfig 4}

        advanceWifiId                       OBJECT-TYPE SYNTAX Integer32
                                            MAX-ACCESS  read-only   STATUS current 
                                            DESCRIPTION "2.4G wifi id"
                                            ::= {apWifiDeviceAdvanceConfig 1}
        rssiMode                            OBJECT-TYPE SYNTAX Integer32{dynamic(1),static(0)}
                                            MAX-ACCESS  read-write   STATUS current 
                                            DESCRIPTION "2.4G rssi mode"
                                            ::= {apWifiDeviceAdvanceConfig 2}
        rssiLow			                    OBJECT-TYPE SYNTAX Integer32 UNITS "dBm" 
                                            MAX-ACCESS  read-write   STATUS current 
                                            DESCRIPTION "2.4G rssi low"
                                            ::= {apWifiDeviceAdvanceConfig 3}

    ----------------------------------------------------------------------------
    -- apWifiDeviceRateConfig
    ----------------------------------------------------------------------------
    apWifiDeviceRateConfig               	OBJECT IDENTIFIER ::= {apWifiDeviceConfig 5}

        rateWifiId                       	OBJECT-TYPE SYNTAX Integer32
                                            MAX-ACCESS  read-only   STATUS current 
                                            DESCRIPTION "2.4G wifi id"
                                            ::= {apWifiDeviceRateConfig 1}
        transBasicRate                      OBJECT-TYPE SYNTAX DisplayString
                                            MAX-ACCESS  read-write   STATUS current 
                                            DESCRIPTION "2.4G transmit basic rate,1,2,5.5,11,6,9,12,18,24,36,48,54,
                                            it can be modified only when the rate mode is manual"
                                            ::= {apWifiDeviceRateConfig 2}
        trans11nRate			            OBJECT-TYPE SYNTAX DisplayString 
                                            MAX-ACCESS  read-write   STATUS current 
                                            DESCRIPTION "2.4G transmit 11n rate, mcs0~mcs15,
                                            it can be modified only when the rate mode is manual"
                                            ::= {apWifiDeviceRateConfig 3}
        rateMode                            OBJECT-TYPE SYNTAX Integer32{auto(0),manual(1)}
                                            MAX-ACCESS  read-write   STATUS current 
                                            DESCRIPTION "2.4G rate mode"
                                            ::= {apWifiDeviceRateConfig 4}
        							
    ----------------------------------------------------------------------------
    -- apWifiDevice5Config
    ----------------------------------------------------------------------------
    apWifiDevice5Config                     OBJECT IDENTIFIER ::= {apConfig 15}   

    ----------------------------------------------------------------------------
    -- apWifiDeviceBasicConfig
    ----------------------------------------------------------------------------
    apWifiDeviceBasic5Config                OBJECT IDENTIFIER ::= {apWifiDevice5Config 1}

        basicWifi5Id                        OBJECT-TYPE SYNTAX Integer32
                                            MAX-ACCESS  read-only   STATUS current 
                                            DESCRIPTION "5G wifi id"
                                            ::= {apWifiDeviceBasic5Config 1}
        wifi5DeviceMac                      OBJECT-TYPE SYNTAX MacAddress
                                            MAX-ACCESS  read-only   STATUS current 
                                            DESCRIPTION "5G wifi mac address"
                                            ::= {apWifiDeviceBasic5Config 2}             
        wifi5DeviceType                     OBJECT-TYPE SYNTAX Integer32{ap-single(0),ap-ms(1),adhoc-single(2),adhoc-ms(3),ap-adhoc(4),sta-adhoc(5),sta-single(6),sta-ms(7)}
                                            MAX-ACCESS  read-only   STATUS current 
                                            DESCRIPTION "5G wifi type"
                                            ::= {apWifiDeviceBasic5Config 3}
            
    ----------------------------------------------------------------------------
    -- apWifiDeviceChannel5Config
    ----------------------------------------------------------------------------
    apWifiDeviceChannel5Config              OBJECT IDENTIFIER ::= {apWifiDevice5Config 2}

        channelWifi5Id                      OBJECT-TYPE SYNTAX Integer32
                                            MAX-ACCESS  read-only   STATUS current 
                                            DESCRIPTION "5G wifi id"
                                            ::= {apWifiDeviceChannel5Config 1}
        channelANMode                       OBJECT-TYPE SYNTAX Integer32{dot11a(1),dot11n(8),dot11a-an(9)}
                                            MAX-ACCESS  read-write   STATUS current 
                                            DESCRIPTION "5G wifi channel abg mode"
                                            ::= {apWifiDeviceChannel5Config 2}
        wifi5ChannelUsing                   OBJECT-TYPE SYNTAX Integer32
                                            MAX-ACCESS  read-only   STATUS current 
                                            DESCRIPTION "5G current wifi channel"
                                            ::= {apWifiDeviceChannel5Config 3}
        wifi5ChannelState                  	OBJECT-TYPE SYNTAX Integer32{static(0),auto(1)}
                                            MAX-ACCESS  read-write   STATUS current 
                                            DESCRIPTION "5G wifi channel type"
                                            ::= {apWifiDeviceChannel5Config 4}
        wifi5AutoChanTime                	OBJECT-TYPE SYNTAX Integer32 UNITS "second"
                                            MAX-ACCESS  read-write   STATUS current 
                                            DESCRIPTION "5G wifi auto channel time"
                                            ::= {apWifiDeviceChannel5Config 5}
        wifi5StaticChannel               	OBJECT-TYPE SYNTAX Integer32 
                                            MAX-ACCESS  read-write   STATUS current 
                                            DESCRIPTION "5G wifi static channel"
                                            ::= {apWifiDeviceChannel5Config 6}
        wifi5AutoChanList                   OBJECT-TYPE SYNTAX DisplayString
                                            MAX-ACCESS  read-write   STATUS current 
                                            DESCRIPTION "5G wifi auto channel list"
                                            ::= {apWifiDeviceChannel5Config 7}
        wifi5RfNum                          OBJECT-TYPE SYNTAX Integer32{one(1),two(2)}
                                            MAX-ACCESS  read-write   STATUS current 
                                            DESCRIPTION "5G rf num"
                                            ::= {apWifiDeviceChannel5Config 8}     
        wifi5BwMode                         OBJECT-TYPE SYNTAX Integer32{b20MHz-only(0), b20MHz-40MHz-auto(1), bw40Hz-only(2)}
                                            MAX-ACCESS  read-write   STATUS current 
                                            DESCRIPTION "5G bw mode"
                                            ::= {apWifiDeviceChannel5Config 9}     
                                    
    ----------------------------------------------------------------------------
    -- apWifiDevicePower5Config
    ----------------------------------------------------------------------------
    apWifiDevicePower5Config                OBJECT IDENTIFIER ::= {apWifiDevice5Config 3}

        powerWifi5Id                        OBJECT-TYPE SYNTAX Integer32
                                            MAX-ACCESS  read-only   STATUS current 
                                            DESCRIPTION "5G wifi id"
                                            ::= {apWifiDevicePower5Config 1}
        wifi5MaxTxPower                     OBJECT-TYPE SYNTAX Integer32    UNITS "dBm"
                                            MAX-ACCESS  read-only   STATUS current 
                                            DESCRIPTION "5G wifi max tx power"
                                            ::= {apWifiDevicePower5Config 2}
        wifi5DecayTxPower                   OBJECT-TYPE SYNTAX Integer32  UNITS "dB"
                                            MAX-ACCESS  read-write   STATUS current 
                                            DESCRIPTION "5G wifi decay tx power"
                                            ::= {apWifiDevicePower5Config 3}
        wifi5TransmitPower                  OBJECT-TYPE SYNTAX Integer32   UNITS "dB"
                                            MAX-ACCESS  read-only   STATUS current 
                                            DESCRIPTION "5G wifi transmit power"
                                            ::= {apWifiDevicePower5Config 4}

    ----------------------------------------------------------------------------
    -- apWifiDeviceAdvance5Config
    ----------------------------------------------------------------------------
    apWifiDeviceAdvance5Config              OBJECT IDENTIFIER ::= {apWifiDevice5Config 4}

        advanceWifi5Id                      OBJECT-TYPE SYNTAX Integer32
                                            MAX-ACCESS  read-only   STATUS current 
                                            DESCRIPTION "5G wifi id"
                                            ::= {apWifiDeviceAdvance5Config 1}
        wifi5RssiMode                       OBJECT-TYPE SYNTAX Integer32{dynamic(1),static(0)}
                                            MAX-ACCESS  read-write   STATUS current 
                                            DESCRIPTION "5G rssi mode"
                                            ::= {apWifiDeviceAdvance5Config 2}
        wifi5RssiLow			            OBJECT-TYPE SYNTAX Integer32 UNITS "dBm" 
                                            MAX-ACCESS  read-write   STATUS current 
                                            DESCRIPTION "5G rssi low"
                                            ::= {apWifiDeviceAdvance5Config 3}                                            

    ----------------------------------------------------------------------------
    -- apWifiDeviceRate5Config
    ----------------------------------------------------------------------------
    apWifiDeviceRate5Config               	OBJECT IDENTIFIER ::= {apWifiDevice5Config 5}

        rateWifi5Id                       	OBJECT-TYPE SYNTAX Integer32
                                            MAX-ACCESS  read-only   STATUS current 
                                            DESCRIPTION "5G wifi id"
                                            ::= {apWifiDeviceRate5Config 1}
        wifi5TransBasicRate                 OBJECT-TYPE SYNTAX DisplayString
                                            MAX-ACCESS  read-write   STATUS current 
                                            DESCRIPTION "5G transmit basic rate,1,2,5.5,11,6,9,12,18,24,36,48,54,
                                            it can be modified only when the rate mode is manual"
                                            ::= {apWifiDeviceRate5Config 2}
        wifi5Trans11nRate			        OBJECT-TYPE SYNTAX DisplayString 
                                            MAX-ACCESS  read-write   STATUS current 
                                            DESCRIPTION "5G transmit 11n rate, mcs0~mcs15,
                                            it can be modified only when the rate mode is manual"
                                            ::= {apWifiDeviceRate5Config 3}
        wifi5RateMode                       OBJECT-TYPE SYNTAX Integer32{auto(0), manual(1)}
                                            MAX-ACCESS  read-write   STATUS current 
                                            DESCRIPTION "5G rate mode"
                                            ::= {apWifiDeviceRate5Config 4}             

    ----------------------------------------------------------------------------
    -- apVapConfig
    ----------------------------------------------------------------------------
    apVapConfig                             OBJECT IDENTIFIER ::= {apConfig 20} 
    
    	vapConfigNum						OBJECT-TYPE SYNTAX Unsigned32
    										MAX-ACCESS read-only  STATUS current
    										DESCRIPTION "vap config num" 
    										::= {apVapConfig 1}   										
    ----------------------------------------------------------------------------
    -- apVapBasic
    ----------------------------------------------------------------------------
    apVapBasicTable                              OBJECT-TYPE
        SYNTAX                  SEQUENCE OF ApVapBasicEntry
        MAX-ACCESS              not-accessible
        STATUS                  current
        DESCRIPTION             ""
        ::= {apVapConfig       10}

        apVapBasicEntry                             OBJECT-TYPE
            SYNTAX                  ApVapBasicEntry
            MAX-ACCESS              not-accessible
            STATUS                  current
            DESCRIPTION             ""
            INDEX                   {ssidBasicIndex}
            ::= {apVapBasicTable      1}

        ApVapBasicEntry  ::= SEQUENCE
        {
            ssidBasicIndex              Unsigned32,
            vapBasicId                       Unsigned32,
            wifiBasicId                      Unsigned32,
            ssidBasicName               DisplayString,
            ssidEnabled                 Unsigned32,
            ssidBroadcast               Unsigned32,
            ssidVlanId                  Unsigned32,
            ssidVlanEnable              Unsigned32,
            vapBssid               		MacAddress,
            maxUserNum                  Unsigned32,
            vapFlowSwitch	            Unsigned32,
            vapUplinkMaxRate            Unsigned32,
            vapDownlinkMaxRate          Unsigned32,
            userUpload                  Unsigned32,
            userDownload                Unsigned32,
            endUserTime                 Unsigned32,
            vapBasicStatus				RowStatus
        }

        ssidBasicIndex                      OBJECT-TYPE SYNTAX Unsigned32
                                            MAX-ACCESS  read-only   STATUS current 
                                            DESCRIPTION "ssid index"
                                            ::= {apVapBasicEntry 1}
        vapBasicId                               OBJECT-TYPE SYNTAX Unsigned32(0..32)
                                            MAX-ACCESS  read-only   STATUS current 
                                            DESCRIPTION "vap id"
                                            ::= {apVapBasicEntry 2}
        wifiBasicId                              OBJECT-TYPE SYNTAX Unsigned32(0..1)
                                            MAX-ACCESS  read-only   STATUS current 
                                            DESCRIPTION "wifi id"
                                            ::= {apVapBasicEntry 3}
        ssidBasicName                       OBJECT-TYPE SYNTAX DisplayString
                                            MAX-ACCESS  read-write   STATUS current 
                                            DESCRIPTION "ssid"
                                            ::= {apVapBasicEntry 4}
        ssidEnabled                         OBJECT-TYPE SYNTAX Unsigned32 {enable(1),disable(0)}
                                            MAX-ACCESS  read-write   STATUS current 
                                            DESCRIPTION "ssid enabled"
                                            ::= {apVapBasicEntry 5}
        ssidBroadcast                       OBJECT-TYPE SYNTAX Unsigned32 {on(0),off(1)}
                                            MAX-ACCESS  read-write   STATUS current 
                                            DESCRIPTION "ssid broadcast enabled"
                                            ::= {apVapBasicEntry 6}
        ssidVlanId                          OBJECT-TYPE SYNTAX Unsigned32(0..4094)
                                            MAX-ACCESS  read-write   STATUS current 
                                            DESCRIPTION "ssid vlan"
                                            ::= {apVapBasicEntry 7}
        ssidVlanEnable                      OBJECT-TYPE SYNTAX Unsigned32{off(0), on(1)}
                                            MAX-ACCESS  read-write   STATUS current 
                                            DESCRIPTION "ssid vlan enabled"
                                            ::= {apVapBasicEntry 8}
        vapBssid		                    OBJECT-TYPE SYNTAX MacAddress
                                            MAX-ACCESS  read-only   STATUS current 
                                            DESCRIPTION "bssid"
                                            ::= {apVapBasicEntry 9}
        maxUserNum                          OBJECT-TYPE SYNTAX Unsigned32(0..128)
                                            MAX-ACCESS  read-write   STATUS current 
                                            DESCRIPTION "ssid max user num"
                                            ::= {apVapBasicEntry 10}
        vapFlowSwitch	                    OBJECT-TYPE SYNTAX Unsigned32 {off(0),on(1)}
                                            MAX-ACCESS  read-write   STATUS current 
                                            DESCRIPTION "ssid max simult traffic"
                                            ::= {apVapBasicEntry 11}
        vapUplinkMaxRate                    OBJECT-TYPE SYNTAX Unsigned32(0..30000) UNITS "Kbps"
                                            MAX-ACCESS  read-write   STATUS current 
                                            DESCRIPTION "vap uplink max rate"
                                            ::= {apVapBasicEntry 12}
        vapDownlinkMaxRate                  OBJECT-TYPE SYNTAX Unsigned32(0..30000) UNITS "Kbps"
                                            MAX-ACCESS  read-write   STATUS current 
                                            DESCRIPTION "vap downlink max rate"
                                            ::= {apVapBasicEntry 13}
        userUpload                          OBJECT-TYPE SYNTAX Unsigned32 UNITS "Kbps"
                                            MAX-ACCESS  read-write   STATUS current 
                                            DESCRIPTION "user upload"
                                            ::= {apVapBasicEntry 14}
        userDownload                        OBJECT-TYPE SYNTAX Unsigned32 UNITS "Kbps"
                                            MAX-ACCESS  read-write   STATUS current 
                                            DESCRIPTION "user download"
                                            ::= {apVapBasicEntry 15}
        endUserTime							OBJECT-TYPE SYNTAX Unsigned32 UNITS "second"
                                            MAX-ACCESS  read-write   STATUS current 
                                            DESCRIPTION "end user idle time"
                                            ::= {apVapBasicEntry 16}                                    
        vapBasicStatus                      OBJECT-TYPE SYNTAX RowStatus{active(1),notInService(2),notReady(3),createAndGo(4),createAndWait(5),destroy(6)}
                                            MAX-ACCESS  read-write   STATUS current 
                                            DESCRIPTION "rowstatus"
                                            ::= {apVapBasicEntry 17}                                                                                        
             
    ----------------------------------------------------------------------------
    -- apVapSecurity
    ----------------------------------------------------------------------------
    apVapSecurityTable                              OBJECT-TYPE
        SYNTAX                  SEQUENCE OF ApVapSecurityEntry
        MAX-ACCESS              not-accessible
        STATUS                  current
        DESCRIPTION             ""
        ::= {apVapConfig       11}

        apVapSecurityEntry                          OBJECT-TYPE
            SYNTAX                  ApVapSecurityEntry
            MAX-ACCESS              not-accessible
            STATUS                  current
            DESCRIPTION             ""
            INDEX                   {securityIndex}
            ::= {apVapSecurityTable      1}

        ApVapSecurityEntry  ::= SEQUENCE
        {
            securityIndex               Unsigned32,
            securityVapId        		Unsigned32,
            securityWifiId              Unsigned32,
            securitySsid                DisplayString,
            authType                    Unsigned32,
            securityMode                Unsigned32,
            encryptType                 Unsigned32,
            wpaKey                      DisplayString,
            wpaKeyRenewal               Unsigned32,
            wepKeyFormat                Unsigned32,
            wepKey   		            DisplayString,
            radiusPort			       	Unsigned32,
            radiusAddress				IpAddress,
            radiusKey				    DisplayString,
            accountPort		            Unsigned32,
            accountAddress              IpAddress,
            accountKey                  DisplayString,
            accountInterval             Unsigned32,
            radiusAgingTime				Unsigned32,
            vapSecuStatus				RowStatus
        }  
        
         securityIndex               		OBJECT-TYPE SYNTAX Unsigned32
                                            MAX-ACCESS  read-only   STATUS current 
                                            DESCRIPTION "ssid index"
                                            ::= {apVapSecurityEntry 1}
         securityVapId               		OBJECT-TYPE SYNTAX Unsigned32
                                            MAX-ACCESS  read-only   STATUS current 
                                            DESCRIPTION "vap id"
                                            ::= {apVapSecurityEntry 2}
         securityWifiId                     OBJECT-TYPE SYNTAX Unsigned32
                                            MAX-ACCESS  read-only   STATUS current 
                                            DESCRIPTION "wifi id"
                                            ::= {apVapSecurityEntry 3}
         securitySsid                		OBJECT-TYPE SYNTAX DisplayString
                                            MAX-ACCESS  read-only   STATUS current 
                                            DESCRIPTION "ssid name"
                                            ::= {apVapSecurityEntry 4}
         authType                    		OBJECT-TYPE SYNTAX Unsigned32{disabled(1), wep(2)}
                                            MAX-ACCESS  read-write   STATUS current 
                                            DESCRIPTION "auth type"
                                            ::= {apVapSecurityEntry 5}
         securityMode                		OBJECT-TYPE SYNTAX Unsigned32{open(1),shared(2),wpa-psk(3),wpa2-psk(4),wpapsk-wap2psk(5),wpa(6),wpa2(7),wpa-wap2(8)}
                                            MAX-ACCESS  read-write   STATUS current 
                                            DESCRIPTION "security mode"
                                            ::= {apVapSecurityEntry 6}
         encryptType                 		OBJECT-TYPE SYNTAX Unsigned32{none(0),tkip(1),aes(2),auto(3)}
                                            MAX-ACCESS  read-write   STATUS current 
                                            DESCRIPTION "encrypt type"
                                            ::= {apVapSecurityEntry 7}
         wpaKey                      		OBJECT-TYPE SYNTAX DisplayString
                                            MAX-ACCESS  read-write   STATUS current 
                                            DESCRIPTION "wpa key"
                                            ::= {apVapSecurityEntry 8}
         wpaKeyRenewal               		OBJECT-TYPE SYNTAX Unsigned32
                                            MAX-ACCESS  read-write   STATUS current 
                                            DESCRIPTION "wpa key renewal"
                                            ::= {apVapSecurityEntry 9}
         wepKeyFormat                		OBJECT-TYPE SYNTAX Unsigned32{wep-64bit-16hex(0),wep-64bit-ascii(1),wep-128bit-16hex(2),wep-128bit-ascii(3)}
                                            MAX-ACCESS  read-write   STATUS current 
                                            DESCRIPTION "wep key format"
                                            ::= {apVapSecurityEntry 10}
         wepKey   		            		OBJECT-TYPE SYNTAX DisplayString
                                            MAX-ACCESS  read-write   STATUS current 
                                            DESCRIPTION "wep key"
                                            ::= {apVapSecurityEntry 11}
         radiusPort			        		OBJECT-TYPE SYNTAX Unsigned32
                                            MAX-ACCESS  read-write   STATUS current 
                                            DESCRIPTION "radius port"
                                            ::= {apVapSecurityEntry 12}
         radiusAddress       				OBJECT-TYPE SYNTAX IpAddress
                                            MAX-ACCESS  read-write   STATUS current 
                                            DESCRIPTION "radius ip address"
                                            ::= {apVapSecurityEntry 13}
         radiusKey		    				OBJECT-TYPE SYNTAX DisplayString
                                            MAX-ACCESS  read-write   STATUS current 
                                            DESCRIPTION "radius key"
                                            ::= {apVapSecurityEntry 14}
         accountPort              			OBJECT-TYPE SYNTAX Unsigned32
                                            MAX-ACCESS  read-write   STATUS current 
                                            DESCRIPTION "account port"
                                            ::= {apVapSecurityEntry 15}
         accountAddress                		OBJECT-TYPE SYNTAX IpAddress
                                            MAX-ACCESS  read-write   STATUS current 
                                            DESCRIPTION "account ip address"
                                            ::= {apVapSecurityEntry 16}
         accountKey                    		OBJECT-TYPE SYNTAX DisplayString
                                            MAX-ACCESS  read-write   STATUS current 
                                            DESCRIPTION "account key"
                                            ::= {apVapSecurityEntry 17}
         accountInterval               		OBJECT-TYPE SYNTAX Unsigned32
                                            MAX-ACCESS  read-write   STATUS current 
                                            DESCRIPTION "account interval"
                                            ::= {apVapSecurityEntry 18}
         radiusAgingTime                    OBJECT-TYPE SYNTAX Unsigned32
                                            MAX-ACCESS  read-write   STATUS current 
                                            DESCRIPTION "radius aging time"
                                            ::= {apVapSecurityEntry 19}
         vapSecuStatus                      OBJECT-TYPE SYNTAX RowStatus
                                            MAX-ACCESS  read-write   STATUS current 
                                            DESCRIPTION "row status"
                                            ::= {apVapSecurityEntry 20}                            

    ----------------------------------------------------------------------------
    -- apAlarmConfig
    ----------------------------------------------------------------------------
    apAlarmConfig                           OBJECT IDENTIFIER ::= {apConfig 30}
    
    	cpuLoadHigh                         OBJECT-TYPE SYNTAX Integer32(0..100)    UNITS "%"
                                            MAX-ACCESS  read-write   STATUS current 
                                            DESCRIPTION "cpu load high"
                                            DEFVAL {90}
                                            ::= {apAlarmConfig 1}
    	cpuLoadLow                          OBJECT-TYPE SYNTAX Integer32(0..100)    UNITS "%"
                                            MAX-ACCESS  read-write   STATUS current 
                                            DESCRIPTION "cpu load low"
                                            DEFVAL {80}
                                            ::= {apAlarmConfig 2}
    	memLoadHigh                         OBJECT-TYPE SYNTAX Integer32(0..100)    UNITS "%"
                                            MAX-ACCESS  read-write   STATUS current 
                                            DESCRIPTION "memory load high"
                                            DEFVAL {95}
                                            ::= {apAlarmConfig 3}
    	memLoadLow                          OBJECT-TYPE SYNTAX Integer32(0..100)    UNITS "%"
                                            MAX-ACCESS  read-write   STATUS current 
                                            DESCRIPTION "memory load low"
                                            DEFVAL {90}
                                            ::= {apAlarmConfig 4}
    ----------------------------------------------------------------------------
    -- apTrapDesConfig
    ----------------------------------------------------------------------------
    apTrapDesConfig                         OBJECT IDENTIFIER ::= {apConfig 40} 
    
    	trapStatus							OBJECT-TYPE SYNTAX Integer32{off(0), on(1)}
    										MAX-ACCESS read-write  STATUS current
    										DESCRIPTION "trap switch" 
    										::= {apTrapDesConfig 1}   										
        trapDestIp							OBJECT-TYPE SYNTAX IpAddress
    										MAX-ACCESS read-write  STATUS current
    										DESCRIPTION "trap destination ip address" 
    										::= {apTrapDesConfig 2}
    	trapDestPort						OBJECT-TYPE SYNTAX Integer32
    										MAX-ACCESS read-write  STATUS current
    										DESCRIPTION "trap destination port" 
    										::= {apTrapDesConfig 3}
    	trapCommunity						OBJECT-TYPE SYNTAX DisplayString
    										MAX-ACCESS read-write  STATUS current
    										DESCRIPTION "trap community" 
    										::= {apTrapDesConfig 4}
    																																					
    ----------------------------------------------------------------------------
    -- apVlanConfig
    ----------------------------------------------------------------------------
    apVlanConfig	                        OBJECT IDENTIFIER ::= {apConfig 50} 
    
    	vlanNum								OBJECT-TYPE SYNTAX Unsigned32
    										MAX-ACCESS read-only  STATUS current
    										DESCRIPTION "vlan num" 
    										::= {apVlanConfig 1}   										
    ----------------------------------------------------------------------------
    -- apVlanTable
    ----------------------------------------------------------------------------
    apVlanTable                          	OBJECT-TYPE
        SYNTAX                  SEQUENCE OF ApVlanEntry
        MAX-ACCESS              not-accessible
        STATUS                  current
        DESCRIPTION             ""
        ::= {apVlanConfig       10}

        apVlanEntry                      	OBJECT-TYPE
            SYNTAX                  ApVlanEntry
            MAX-ACCESS              not-accessible
            STATUS                  current
            DESCRIPTION             ""
            INDEX                   {vlanIndex}
            ::= {apVlanTable      1}

        ApVlanEntry  ::= SEQUENCE
        {
            vlanIndex                   Unsigned32,
            vlanId	                   	Unsigned32,
            vlanName                 	DisplayString,
            vlanNvramId                 Unsigned32,
            vlanPrio                    Unsigned32,
            vlanRowStatus            	RowStatus
        }

        vlanIndex                           OBJECT-TYPE SYNTAX Unsigned32
                                            MAX-ACCESS  read-only   STATUS current 
                                            DESCRIPTION "index"
                                            ::= {apVlanEntry 1}
        vlanId                              OBJECT-TYPE SYNTAX Unsigned32(0..31)
                                            MAX-ACCESS  read-only   STATUS current 
                                            DESCRIPTION "vlan id"
                                            ::= {apVlanEntry 2}
        vlanName                            OBJECT-TYPE SYNTAX DisplayString
                                            MAX-ACCESS  read-write   STATUS current 
                                            DESCRIPTION "vlan name"
                                            ::= {apVlanEntry 3}
        vlanNvramId                         OBJECT-TYPE SYNTAX Unsigned32
                                            MAX-ACCESS  read-only   STATUS current 
                                            DESCRIPTION "vlan nvram id"
                                            ::= {apVlanEntry 4}
        vlanPrio                            OBJECT-TYPE SYNTAX Unsigned32{auto(8),priority0(0),priority1(1),priority2(2),priority3(3),priority4(4),priority5(5),priority6(6),priority7(7)}
                                            MAX-ACCESS  read-write   STATUS current 
                                            DESCRIPTION "vlan port"
                                            ::= {apVlanEntry 5}
        vlanRowStatus                       OBJECT-TYPE SYNTAX RowStatus
                                            MAX-ACCESS  read-write   STATUS current 
                                            DESCRIPTION "row status"
                                            ::= {apVlanEntry 6}                                                                                              
    ----------------------------------------------------------------------------
    -- apSsidSetup
    ----------------------------------------------------------------------------
    apSsidSetup	                            OBJECT IDENTIFIER ::= {apConfig 60} 
    
    	ssidNum								OBJECT-TYPE SYNTAX Unsigned32
    										MAX-ACCESS read-only  STATUS current
    										DESCRIPTION "ssid num" 
    										::= {apSsidSetup 1}   										
    ----------------------------------------------------------------------------
    -- apSsidTable
    ----------------------------------------------------------------------------
    apSsidTable                          	OBJECT-TYPE
        SYNTAX                  SEQUENCE OF ApSsidEntry
        MAX-ACCESS              not-accessible
        STATUS                  current
        DESCRIPTION             ""
        ::= {apSsidSetup       10}

        apSsidEntry                      	OBJECT-TYPE
            SYNTAX                  ApSsidEntry
            MAX-ACCESS              not-accessible
            STATUS                  current
            DESCRIPTION             ""
            INDEX                   {ssidIndex}
            ::= {apSsidTable      1}

        ApSsidEntry  ::= SEQUENCE
        {
            ssidConfigIndex                   Unsigned32,
            ssidWifiId	                Unsigned32,
            ssidVapId					Unsigned32,
            ssidName                 	DisplayString,
            ssidRowStatus            	RowStatus
        }

        ssidConfigIndex                           OBJECT-TYPE SYNTAX Unsigned32
                                            MAX-ACCESS  read-only   STATUS current 
                                            DESCRIPTION "index"
                                            ::= {apSsidEntry 1}
        ssidWifiId                          OBJECT-TYPE SYNTAX Unsigned32(0..1)
                                            MAX-ACCESS  read-only   STATUS current 
                                            DESCRIPTION "wifi id"
                                            ::= {apSsidEntry 2}
        ssidVapId                           OBJECT-TYPE SYNTAX Unsigned32(0..31)
                                            MAX-ACCESS  read-only   STATUS current 
                                            DESCRIPTION "vap id"
                                            ::= {apSsidEntry 3}
        ssidName                            OBJECT-TYPE SYNTAX DisplayString
                                            MAX-ACCESS  read-only   STATUS current 
                                            DESCRIPTION "ssid name"
                                            ::= {apSsidEntry 4}
        ssidRowStatus                       OBJECT-TYPE SYNTAX RowStatus
                                            MAX-ACCESS  read-only   STATUS current 
                                            DESCRIPTION "row status"
                                            ::= {apSsidEntry 5}  

    ----------------------------------------------------------------------------
    -- clientBlackWhiteConfig
    ----------------------------------------------------------------------------
    clientBlackWhiteConfig	                OBJECT IDENTIFIER ::= {apConfig 61}

        clientSsidIndex							OBJECT-TYPE SYNTAX Integer32
                                            MAX-ACCESS  read-write   STATUS current 
                                            DESCRIPTION "ssid index"
                                            ::= {clientBlackWhiteConfig 1}
        mac                                 OBJECT-TYPE SYNTAX MacAddress
                                            MAX-ACCESS  read-write   STATUS current 
                                            DESCRIPTION "mac"
                                            ::= {clientBlackWhiteConfig 2}
        type                                OBJECT-TYPE SYNTAX Integer32{black(1),white(2)}
                                            MAX-ACCESS  read-write   STATUS current 
                                            DESCRIPTION "mac"
                                            ::= {clientBlackWhiteConfig 3}
        status                      	    OBJECT-TYPE SYNTAX Integer32{modify(1),add(2),delete(3)}
                                            MAX-ACCESS  read-write   STATUS current 
                                            DESCRIPTION ""
                                            ::= {clientBlackWhiteConfig 4}
   																						    																																	                                                                                                                                    
    ----------------------------------------------------------------------------
    -- domainFilterConfig
    ----------------------------------------------------------------------------
    domainFilterConfig	                	OBJECT IDENTIFIER ::= {apConfig 62}

        domainSsidIndex							OBJECT-TYPE SYNTAX Integer32
                                            MAX-ACCESS  read-write   STATUS current 
                                            DESCRIPTION "ssid index"
                                            ::= {domainFilterConfig 1}
        domain                              OBJECT-TYPE SYNTAX DisplayString
                                            MAX-ACCESS  read-write   STATUS current 
                                            DESCRIPTION "mac"
                                            ::= {domainFilterConfig 2}
        domainType                                OBJECT-TYPE SYNTAX Integer32{black(1),white(2)}
                                            MAX-ACCESS  read-write   STATUS current 
                                            DESCRIPTION "mac"
                                            ::= {domainFilterConfig 3}
        domainStatus                      	    OBJECT-TYPE SYNTAX Integer32{normal(0), add(1), delete(2), update(3)}
                                            MAX-ACCESS  read-write   STATUS current 
                                            DESCRIPTION ""
                                            ::= {domainFilterConfig 4}
                                            
    ----------------------------------------------------------------------------
    -- gwApSsidInfoConfig
    ----------------------------------------------------------------------------
    gwApSsidInfoConfig	                	OBJECT IDENTIFIER ::= {apConfig 63}

        apMac                               OBJECT-TYPE SYNTAX MacAddress
                                            MAX-ACCESS  read-write   STATUS current 
                                            DESCRIPTION "mac"
                                            ::= {gwApSsidInfoConfig 1}
        gwApSsidIndex                           OBJECT-TYPE SYNTAX Integer32
                                            MAX-ACCESS  read-write   STATUS current 
                                            DESCRIPTION ""
                                            ::= {gwApSsidInfoConfig 2}
        gwApVapName                             OBJECT-TYPE SYNTAX DisplayString
                                            MAX-ACCESS  read-write   STATUS current 
                                            DESCRIPTION ""
                                            ::= {gwApSsidInfoConfig 3}
        radioType                           OBJECT-TYPE SYNTAX Integer32{wifi24(0),wifi5(1)}
                                            MAX-ACCESS  read-write   STATUS current 
                                            DESCRIPTION ""
                                            ::= {gwApSsidInfoConfig 4}
        gwApSsid                                OBJECT-TYPE SYNTAX DisplayString
                                            MAX-ACCESS  read-write   STATUS current 
                                            DESCRIPTION ""
                                            ::= {gwApSsidInfoConfig 5}
        gwApDefault                             OBJECT-TYPE SYNTAX Integer32{non-default(0),default(1)}
                                            MAX-ACCESS  read-write   STATUS current 
                                            DESCRIPTION ""
                                            ::= {gwApSsidInfoConfig 6}
        gwApUpRate                              OBJECT-TYPE SYNTAX Integer32 UNITS "KBps"
                                            MAX-ACCESS  read-write   STATUS current 
                                            DESCRIPTION ""
                                            ::= {gwApSsidInfoConfig 7}
        gwApDownRate                            OBJECT-TYPE SYNTAX Integer32 UNITS "KBps"
                                            MAX-ACCESS  read-write   STATUS current 
                                            DESCRIPTION ""
                                            ::= {gwApSsidInfoConfig 8}
        gwApPortalUrl                           OBJECT-TYPE SYNTAX DisplayString
                                            MAX-ACCESS  read-write   STATUS current 
                                            DESCRIPTION ""
                                            ::= {gwApSsidInfoConfig 9}
        onlineContrlTime                    OBJECT-TYPE SYNTAX Integer32 UNITS "minutes"
                                            MAX-ACCESS  read-write   STATUS current 
                                            DESCRIPTION ""
                                            ::= {gwApSsidInfoConfig 10}
        gwApFlowOffTime                         OBJECT-TYPE SYNTAX Integer32 UNITS "minutes"
                                            MAX-ACCESS  read-write   STATUS current 
                                            DESCRIPTION ""
                                            ::= {gwApSsidInfoConfig 11}
        gwApStatus								OBJECT-TYPE SYNTAX Integer32{modify(1),add(2),delete(3)}
                                            MAX-ACCESS  read-write   STATUS current 
                                            DESCRIPTION ""
                                            ::= {gwApSsidInfoConfig 12}
                                            
    ----------------------------------------------------------------------------
    -- userConfig
    ----------------------------------------------------------------------------
    userConfig	                            OBJECT IDENTIFIER ::= {apConfig 70} 
    
    	action								OBJECT-TYPE SYNTAX Integer32 {login(1),logout(2),authRequest(3)}
    										MAX-ACCESS read-write  STATUS current
    										DESCRIPTION " " 
    										::= {userConfig 1}
    	userMac                             OBJECT-TYPE SYNTAX MacAddress
    										MAX-ACCESS read-write  STATUS current
    										DESCRIPTION " " 
    										::= {userConfig 2}
    	userAuthType						OBJECT-TYPE SYNTAX Integer32 {userpasswd(1),coupon(2),fixedpasswd(3),phone(4),qq(5),weibo(6),nopasswd(7),weixin(8),alipay(9)}
    										MAX-ACCESS read-write  STATUS current
    										DESCRIPTION " " 
    										::= {userConfig 3}
    	userId								OBJECT-TYPE SYNTAX DisplayString
    										MAX-ACCESS read-write  STATUS current
    										DESCRIPTION " " 
    										::= {userConfig 4}
    	userTimeLimit						OBJECT-TYPE SYNTAX Integer32 UNITS"min"
    										MAX-ACCESS read-write  STATUS current
    										DESCRIPTION " " 
    										::= {userConfig 5}			
    	userAuthCommit						OBJECT-TYPE SYNTAX Integer32 {normal(0),commit(1)}
    										MAX-ACCESS read-write  STATUS current
    										DESCRIPTION " " 
    										::= {userConfig 6}
    	userUrl								OBJECT-TYPE SYNTAX DisplayString
    										MAX-ACCESS read-write  STATUS current
    										DESCRIPTION " " 
    										::= {userConfig 7}
    	userRequestId						OBJECT-TYPE SYNTAX Integer32
    										MAX-ACCESS read-write  STATUS current
    										DESCRIPTION " " 
    										::= {userConfig 8}
    	userAuthResult						OBJECT-TYPE SYNTAX Integer32 {success(0), fail(1)}
    										MAX-ACCESS read-write  STATUS current
    										DESCRIPTION " " 
    										::= {userConfig 9}
    	userThreadIndex						OBJECT-TYPE SYNTAX Integer32
    										MAX-ACCESS read-write  STATUS current
    										DESCRIPTION "this item used by wifidog to identify diffrent thread" 
    										::= {userConfig 10}																									
    																														   										
    ----------------------------------------------------------------------------
    -- gwSsidConfig
    ----------------------------------------------------------------------------
    gwSsidConfig	                        OBJECT IDENTIFIER ::= {apConfig 71} 
    
    	gwApssid							OBJECT-TYPE SYNTAX DisplayString
    										MAX-ACCESS read-write  STATUS current
    										DESCRIPTION " " 
    										::= {gwSsidConfig 1}
    ----------------------------------------------------------------------------
    -- gwAuthConfig
    ----------------------------------------------------------------------------
    gwAuthConfig	                        OBJECT IDENTIFIER ::= {apConfig 72} 
    
    	switch								OBJECT-TYPE SYNTAX Integer32{off(0), on(1)}
    										MAX-ACCESS read-write  STATUS current
    										DESCRIPTION " " 
    										::= {gwAuthConfig 1}
    	webAuth								OBJECT-TYPE SYNTAX Integer32{off(0), on(1)}
    										MAX-ACCESS read-write  STATUS current
    										DESCRIPTION " " 
    										::= {gwAuthConfig 2}
    	offline								OBJECT-TYPE SYNTAX Integer32 UNITS "second"
    										MAX-ACCESS read-write  STATUS current
    										DESCRIPTION " " 
    										::= {gwAuthConfig 3}
    	reverify							OBJECT-TYPE SYNTAX Integer32 UNITS "min"
    										MAX-ACCESS read-write  STATUS current
    										DESCRIPTION " " 
    										::= {gwAuthConfig 4}
    	freeMac								OBJECT-TYPE SYNTAX DisplayString
    										MAX-ACCESS read-write  STATUS current
    										DESCRIPTION " " 
    										::= {gwAuthConfig 5}
    	authCfgCommit						OBJECT-TYPE SYNTAX Integer32{normal(0), commit(1)}
    										MAX-ACCESS read-write  STATUS current
    										DESCRIPTION " " 
    										::= {gwAuthConfig 6}
    																					
    ----------------------------------------------------------------------------
    -- gwBatchBlackWhiteListConfig
    ----------------------------------------------------------------------------
    gwBatchBlackWhiteListConfig	            OBJECT IDENTIFIER ::= {apConfig 73} 
    
    	listType							OBJECT-TYPE SYNTAX Unsigned32{white(1), black(2)}
    										MAX-ACCESS read-write  STATUS current
    										DESCRIPTION " " 
    										::= {gwBatchBlackWhiteListConfig 1}
    	macList								OBJECT-TYPE SYNTAX DisplayString
    										MAX-ACCESS read-write  STATUS current
    										DESCRIPTION " " 
    										::= {gwBatchBlackWhiteListConfig 2}      
    	macStatus							OBJECT-TYPE SYNTAX Integer32{normal(0), add(1), delete(2), update(3)}
    										MAX-ACCESS read-write  STATUS current
    										DESCRIPTION " " 
    										::= {gwBatchBlackWhiteListConfig 3}		 
    										
    ----------------------------------------------------------------------------
    -- gwUserSpeedConfig
    ----------------------------------------------------------------------------
    gwUserSpeedConfig	            		OBJECT IDENTIFIER ::= {apConfig 74} 
    
    	uploadMax							OBJECT-TYPE SYNTAX Integer32 UNITS"KB"
    										MAX-ACCESS read-write  STATUS current
    										DESCRIPTION " " 
    										::= {gwUserSpeedConfig 1}
    	downloadMax							OBJECT-TYPE SYNTAX Integer32 UNITS"KB"
    										MAX-ACCESS read-write  STATUS current
    										DESCRIPTION " " 
    										::= {gwUserSpeedConfig 2}
    	userSpeedCfgCommit					OBJECT-TYPE SYNTAX Integer32{normal(0), commit(1)}
    										MAX-ACCESS read-write  STATUS current
    										DESCRIPTION " " 
    										::= {gwUserSpeedConfig 3}				
    										
    ----------------------------------------------------------------------------
    -- gwWhiteUserSpeedConfig
    ----------------------------------------------------------------------------
    gwWhiteUserSpeedConfig	            	OBJECT IDENTIFIER ::= {apConfig 75} 
    
    	whiteUploadMax						OBJECT-TYPE SYNTAX Integer32 UNITS"KB"
    										MAX-ACCESS read-write  STATUS current
    										DESCRIPTION " " 
    										::= {gwWhiteUserSpeedConfig 1}
    	whiteDownloadMax					OBJECT-TYPE SYNTAX Integer32 UNITS"KB"
    										MAX-ACCESS read-write  STATUS current
    										DESCRIPTION " " 
    										::= {gwWhiteUserSpeedConfig 2}
    	whiteSpeedCfgCommit					OBJECT-TYPE SYNTAX Integer32{normal(0), commit(1)}
    										MAX-ACCESS read-write  STATUS current
    										DESCRIPTION " " 
    										::= {gwWhiteUserSpeedConfig 3}				
    										
    ----------------------------------------------------------------------------
    -- userLogoutConfig
    ----------------------------------------------------------------------------
    userLogoutConfig	            		OBJECT IDENTIFIER ::= {apConfig 76} 
    
    	logoutStatus						OBJECT-TYPE SYNTAX Integer32{off(0), on(1)}
    										MAX-ACCESS read-write  STATUS current
    										DESCRIPTION " " 
    										::= {userLogoutConfig 1}
    	timeCondition					    OBJECT-TYPE SYNTAX Integer32
    										MAX-ACCESS read-write  STATUS current
    										DESCRIPTION " " 
    										::= {userLogoutConfig 2}
    	flowCondition					    OBJECT-TYPE SYNTAX Integer32 UNITS "KB"
    										MAX-ACCESS read-write  STATUS current
    										DESCRIPTION " " 
    										::= {userLogoutConfig 3}
    	logoutCommit						OBJECT-TYPE SYNTAX Integer32{normal(0), commit(1)}
    										MAX-ACCESS read-write  STATUS current
    										DESCRIPTION " " 
    										::= {userLogoutConfig 4}												    																																											   																						    																																	                                                                                                                                    

    ----------------------------------------------------------------------------
    -- getSecretKeyConfig
    ----------------------------------------------------------------------------
    getSecretKeyConfig	            		OBJECT IDENTIFIER ::= {apConfig 77} 
    
    	interval							OBJECT-TYPE SYNTAX Integer32 UNITS"second"
    										MAX-ACCESS read-write  STATUS current
    										DESCRIPTION " " 
    										::= {getSecretKeyConfig 1}

    ----------------------------------------------------------------------------
    -- dhcpSeverConfig
    ----------------------------------------------------------------------------
    dhcpSeverConfig	            			OBJECT IDENTIFIER ::= {apConfig 78} 
    
		dhcpCommit                          OBJECT-TYPE SYNTAX Integer32{normal(0), commit(1)}
    										MAX-ACCESS read-write  STATUS current
    										DESCRIPTION " " 
    										::= {dhcpSeverConfig 1}
    	ipStart								OBJECT-TYPE SYNTAX IpAddress
    										MAX-ACCESS read-write  STATUS current
    										DESCRIPTION " " 
    										::= {dhcpSeverConfig 2}
    	dhcpIpNum							OBJECT-TYPE SYNTAX Integer32
    										MAX-ACCESS read-write  STATUS current
    										DESCRIPTION " " 
    										::= {dhcpSeverConfig 3}
    	ipGateWay                           OBJECT-TYPE SYNTAX IpAddress
    										MAX-ACCESS read-write  STATUS current
    										DESCRIPTION " " 
    										::= {dhcpSeverConfig 4}
    	ipMask                              OBJECT-TYPE SYNTAX IpAddress
    										MAX-ACCESS read-write  STATUS current
    										DESCRIPTION " " 
    										::= {dhcpSeverConfig 5}
    	ipDns								OBJECT-TYPE SYNTAX IpAddress
    										MAX-ACCESS read-write  STATUS current
    										DESCRIPTION " " 
    										::= {dhcpSeverConfig 6}
    	lanIp								OBJECT-TYPE SYNTAX IpAddress
    										MAX-ACCESS read-write  STATUS current
    										DESCRIPTION " " 
    										::= {dhcpSeverConfig 7}				

    ----------------------------------------------------------------------------
    -- ssidMacBWListConfig
    ----------------------------------------------------------------------------
    ssidMacBWListConfig	            		OBJECT IDENTIFIER ::= {apConfig 79} 
    
		macListSsid                         OBJECT-TYPE SYNTAX DisplayString
    										MAX-ACCESS read-write  STATUS current
    										DESCRIPTION " " 
    										::= {ssidMacBWListConfig 1}
    	macListType							OBJECT-TYPE SYNTAX Integer32{black(1), white(2)}
    										MAX-ACCESS read-write  STATUS current
    										DESCRIPTION " " 
    										::= {ssidMacBWListConfig 2}
    	ssidMacList							OBJECT-TYPE SYNTAX DisplayString
    										MAX-ACCESS read-write  STATUS current
    										DESCRIPTION " " 
    										::= {ssidMacBWListConfig 3}
    	macListStatus                       OBJECT-TYPE SYNTAX Integer32{normal(0), add(1), delete(2), update(3)}
    										MAX-ACCESS read-write  STATUS current
    										DESCRIPTION " " 
    										::= {ssidMacBWListConfig 4}
    	macListSsidRadioId					OBJECT-TYPE SYNTAX Integer32
    										MAX-ACCESS read-write  STATUS current
    										DESCRIPTION " " 
    										::= {ssidMacBWListConfig 5}
    	macListApMac						OBJECT-TYPE SYNTAX DisplayString
    										MAX-ACCESS read-write  STATUS current
    										DESCRIPTION " " 
    										::= {ssidMacBWListConfig 6}							
    										
    ----------------------------------------------------------------------------
    -- gwQosConfig
    ----------------------------------------------------------------------------
    gwQosConfig	            				OBJECT IDENTIFIER ::= {apConfig 80} 
    
		gwQosUpRate                         OBJECT-TYPE SYNTAX Integer32
    										MAX-ACCESS read-write  STATUS current
    										DESCRIPTION " " 
    										::= {gwQosConfig 1}
    	gwQosDwRate							OBJECT-TYPE SYNTAX Integer32
    										MAX-ACCESS read-write  STATUS current
    										DESCRIPTION " " 
    										::= {gwQosConfig 2}
    	gwQosCommit							OBJECT-TYPE SYNTAX Integer32{normal(0), commit(1)}
    										MAX-ACCESS read-write  STATUS current
    										DESCRIPTION " " 
    										::= {gwQosConfig 3}		
    										                                                                  
   	----------------------------------------------------------------------------
    -- hotSpotConfig
    ----------------------------------------------------------------------------                                          
   	hotSpotConfig                           OBJECT IDENTIFIER ::= {apConfig 90}     
   	
   		wifiDogSwitch                    	OBJECT-TYPE SYNTAX Integer32{off(0), on(1)}    
                                            MAX-ACCESS  read-write   STATUS current 
                                            DESCRIPTION " "
                                            ::= {hotSpotConfig 1}  
        deviceHotspotName                   OBJECT-TYPE SYNTAX DisplayString    
                                            MAX-ACCESS  read-write   STATUS current 
                                            DESCRIPTION " "
                                            ::= {hotSpotConfig 2}
        deviceHotspotUrl                    OBJECT-TYPE SYNTAX DisplayString   
                                            MAX-ACCESS  read-write   STATUS current 
                                            DESCRIPTION " "
                                            ::= {hotSpotConfig 3}   
        deviceHotspotbackUrl                OBJECT-TYPE SYNTAX DisplayString   
                                            MAX-ACCESS  read-write   STATUS current 
                                            DESCRIPTION " "
                                            ::= {hotSpotConfig 4}                                 
        deviceHotspotPath                    OBJECT-TYPE SYNTAX DisplayString    
                                            MAX-ACCESS  read-write   STATUS current 
                                            DESCRIPTION " "
                                            ::= {hotSpotConfig 5}										
                                        
   	----------------------------------------------------------------------------
    -- netSniffConfig
    ----------------------------------------------------------------------------                                          
   	netSniffConfig                          OBJECT IDENTIFIER ::= {apConfig 91}     
   	
   		sniffGlobalEnable                   OBJECT-TYPE SYNTAX DisplayString    
                                            MAX-ACCESS  read-write   STATUS current 
                                            DESCRIPTION " "
                                            ::= {netSniffConfig 1}  
        sniffServerIp                       OBJECT-TYPE SYNTAX IpAddress    
                                            MAX-ACCESS  read-write   STATUS current 
                                            DESCRIPTION " "
                                            ::= {netSniffConfig 2}
        sniffDevId                    		OBJECT-TYPE SYNTAX DisplayString   
                                            MAX-ACCESS  read-write   STATUS current 
                                            DESCRIPTION " "
                                            ::= {netSniffConfig 3}   
        sniffLocationId                		OBJECT-TYPE SYNTAX DisplayString   
                                            MAX-ACCESS  read-write   STATUS current 
                                            DESCRIPTION " "
                                            ::= {netSniffConfig 4}                                 
        sniffLocationName                   OBJECT-TYPE SYNTAX DisplayString    
                                            MAX-ACCESS  read-write   STATUS current 
                                            DESCRIPTION " "
                                            ::= {netSniffConfig 5}   
										                                     
   	----------------------------------------------------------------------------
    -- collectInfoConfig
    ----------------------------------------------------------------------------                                          
   	collectInfoConfig                       OBJECT IDENTIFIER ::= {apConfig 92}     
   	
   		locatorSw                   		OBJECT-TYPE SYNTAX Integer32{off(0), on(1)}    
                                            MAX-ACCESS  read-write   STATUS current 
                                            DESCRIPTION " "
                                            ::= {collectInfoConfig 1}  
        locatorStorageMode                  OBJECT-TYPE SYNTAX Integer32{server(0), locator(1),serverandlocator(2)}    
                                            MAX-ACCESS  read-write   STATUS current 
                                            DESCRIPTION " "
                                            ::= {collectInfoConfig 2}
        locatorServerIp                    	OBJECT-TYPE SYNTAX IpAddress  
                                            MAX-ACCESS  read-write   STATUS current 
                                            DESCRIPTION " "
                                            ::= {collectInfoConfig 3}   
        locatorServerPort                		OBJECT-TYPE SYNTAX Integer32   
                                            MAX-ACCESS  read-write   STATUS current 
                                            DESCRIPTION " "
                                            ::= {collectInfoConfig 4}                                 
        locatorLayer4Protocol                    OBJECT-TYPE SYNTAX DisplayString    
                                            MAX-ACCESS  read-write   STATUS current 
                                            DESCRIPTION " "
                                            ::= {collectInfoConfig 5} 
        locatorEngine                    	OBJECT-TYPE SYNTAX DisplayString    
                                            MAX-ACCESS  read-write   STATUS current 
                                            DESCRIPTION " "
                                            ::= {collectInfoConfig 6}  
        locatorReportInterval                       OBJECT-TYPE SYNTAX Integer32    
                                            MAX-ACCESS  read-write   STATUS current 
                                            DESCRIPTION " "
                                            ::= {collectInfoConfig 7}
        stadctRptInterval                   		OBJECT-TYPE SYNTAX Integer32   
                                            MAX-ACCESS  read-write   STATUS current 
                                            DESCRIPTION " "
                                            ::= {collectInfoConfig 8}   
        stadctQuitInterval                		OBJECT-TYPE SYNTAX Integer32   
                                            MAX-ACCESS  read-write   STATUS current 
                                            DESCRIPTION " "
                                            ::= {collectInfoConfig 9}                                 
        locatorScanType                    OBJECT-TYPE SYNTAX DisplayString    
                                            MAX-ACCESS  read-write   STATUS current 
                                            DESCRIPTION " "
                                            ::= {collectInfoConfig 10}
        locatorScanPriority                    	OBJECT-TYPE SYNTAX DisplayString    
                                            MAX-ACCESS  read-write   STATUS current 
                                            DESCRIPTION " "
                                            ::= {collectInfoConfig 11}  
        locatorScanChannel                       OBJECT-TYPE SYNTAX DisplayString    
                                            MAX-ACCESS  read-write   STATUS current 
                                            DESCRIPTION " "
                                            ::= {collectInfoConfig 12}
        locatorFilterMode                    		OBJECT-TYPE SYNTAX Integer32{off(0), distance(1),rssi(2)}   
                                            MAX-ACCESS  read-write   STATUS current 
                                            DESCRIPTION " "
                                            ::= {collectInfoConfig 13}   
        locatorRssiFilter                		OBJECT-TYPE SYNTAX  Integer32   
                                            MAX-ACCESS  read-write   STATUS current 
                                            DESCRIPTION " "
                                            ::= {collectInfoConfig 14}                                 
        locatorDistanceFilter                    OBJECT-TYPE SYNTAX Integer32    
                                            MAX-ACCESS  read-write   STATUS current 
                                            DESCRIPTION " "
                                            ::= {collectInfoConfig 15}
    ----------------------------------------------------------------------------
    -- l2tpInfoConfig
    ----------------------------------------------------------------------------                                          
   	l2tpInfoConfig                       OBJECT IDENTIFIER ::= {apConfig 93}   
   	
   	   l2tpCommit                		OBJECT-TYPE SYNTAX Integer32{off(0), on(1)}    
                                            MAX-ACCESS  read-write   STATUS current 
                                            DESCRIPTION " "
                                            ::= {l2tpInfoConfig 1}    
       l2tpServerIp                    	OBJECT-TYPE SYNTAX IpAddress  
                                            MAX-ACCESS  read-write   STATUS current 
                                            DESCRIPTION " "
                                            ::= {l2tpInfoConfig 2}     
       l2tpUsrName                   OBJECT-TYPE SYNTAX DisplayString    
                                            MAX-ACCESS  read-write   STATUS current 
                                            DESCRIPTION " "
                                            ::= {l2tpInfoConfig 3}
                                              
       l2tpUsrPass                   OBJECT-TYPE SYNTAX DisplayString    
                                            MAX-ACCESS  read-write   STATUS current 
                                            DESCRIPTION " "
                                            ::= {l2tpInfoConfig 4}
                                                                    
       l2tpClientIp                    	OBJECT-TYPE SYNTAX IpAddress  
                                            MAX-ACCESS  read-write   STATUS current 
                                            DESCRIPTION " "
                                            ::= {l2tpInfoConfig 5}    
                                                                    
       l2tpClientStatue                    OBJECT-TYPE SYNTAX Integer32{off(0), on(1)}    
                                            MAX-ACCESS  read-write   STATUS current 
                                            DESCRIPTION " "
                                            ::= {l2tpInfoConfig 6}    
                                                                    
       l2tpClientMsg                    	 OBJECT-TYPE SYNTAX DisplayString    
                                            MAX-ACCESS  read-write   STATUS current 
                                            DESCRIPTION " "
                                            ::= {l2tpInfoConfig 7} 
       l2tpPeerClientIp                    	OBJECT-TYPE SYNTAX IpAddress  
                                            MAX-ACCESS  read-write   STATUS current 
                                            DESCRIPTION " "
                                            ::= {l2tpInfoConfig 8}  
       
										
     ----------------------------------------------------------------------------
    -- apAlarm
    ----------------------------------------------------------------------------
    apAlarm                                 OBJECT IDENTIFIER ::= {gbcom 12}
    ----------------------------------------------------------------------------
    -- apAlarmTrap
    ----------------------------------------------------------------------------
    apAlarmTrap                             OBJECT IDENTIFIER ::= {apAlarm 10}
    ----------------------------------------------------------------------------
    -- apSysAlarmTrap
    ----------------------------------------------------------------------------
    apSysAlarmTrap                          OBJECT IDENTIFIER ::= {apAlarmTrap 1}

        apWarmStartTrap                     NOTIFICATION-TYPE
                                            OBJECTS { alarmSn, alarmNeName, alarmLevel, alarmType, alarmReasonID, alarmReason, alarmRaiseTime, alarmStatus, alarmTitle, alarmInfo }
                                            STATUS current
                                            DESCRIPTION "ap warm system restart"
                                            ::= {apSysAlarmTrap 1}

        apColdStartTrap                     NOTIFICATION-TYPE
                                            OBJECTS { alarmSn, alarmNeName, alarmLevel, alarmType, alarmReasonID, alarmReason, alarmRaiseTime, alarmStatus, alarmTitle, alarmInfo }
                                            STATUS current
                                            DESCRIPTION "ap cold start"
                                            ::= {apSysAlarmTrap 2}

        apCpuUsageTooHighTrap               NOTIFICATION-TYPE
                                            OBJECTS { alarmSn, alarmNeName, alarmLevel, alarmType, alarmReasonID, alarmReason, alarmRaiseTime, alarmStatus, alarmTitle, alarmInfo }
                                            STATUS current
                                            DESCRIPTION "ap cpu usage too high"
                                            ::= {apSysAlarmTrap 3}

        apCpuUsageTooHighClearTrap          NOTIFICATION-TYPE
                                            OBJECTS { alarmSn, alarmNeName, alarmLevel, alarmType, alarmReasonID, alarmReason, alarmRaiseTime, alarmStatus, alarmTitle, alarmInfo }
                                            STATUS current
                                            DESCRIPTION "ap cpu usage too high clear"
                                            ::= {apSysAlarmTrap 4}

        apMemUsageTooHighTrap               NOTIFICATION-TYPE
                                            OBJECTS { alarmSn, alarmNeName, alarmLevel, alarmType, alarmReasonID, alarmReason, alarmRaiseTime, alarmStatus, alarmTitle, alarmInfo }
                                            STATUS current
                                            DESCRIPTION "ap memory usage too high"
                                            ::= {apSysAlarmTrap 5}

        apMemUsageTooHighClearTrap          NOTIFICATION-TYPE
                                            OBJECTS { alarmSn, alarmNeName, alarmLevel, alarmType, alarmReasonID, alarmReason, alarmRaiseTime, alarmStatus, alarmTitle, alarmInfo }
                                            STATUS current
                                            DESCRIPTION "ap memory usage too high clear"
                                            ::= {apSysAlarmTrap 6}

        apDiscoverTrap                      NOTIFICATION-TYPE
                                            OBJECTS { sysMacAddress, sysIpAddress, sysManageState, modelId, currentVersion, softwareVersion, hardwareVersion, modelName, hardwareType, boardVersion, sysModel, devType, sysHotId, sysName, sendOfflineConfigFile}
                                            STATUS current
                                            DESCRIPTION "ap discover cms trap"
                                            ::= {apSysAlarmTrap 7}
                                               
        apFileTransStateTrap                NOTIFICATION-TYPE
                                            OBJECTS { sysMacAddress, softwareVersion, targetVersion, transStatus, fileType }
                                            STATUS current
                                            DESCRIPTION "ap file transmit state trap"
                                            ::= {apSysAlarmTrap 8}
                                            
        apConfigUpdateTrap					NOTIFICATION-TYPE
                                            OBJECTS { updateOid, oldValue, newValue, oidType }
                                            STATUS current
                                            DESCRIPTION "ap config update trap"
                                            ::= {apSysAlarmTrap 9}
                                            
        apFaultTrap                         NOTIFICATION-TYPE
                                            OBJECTS { alarmSn, alarmNeName, alarmLevel, alarmType, alarmReasonID, alarmReason, alarmRaiseTime, alarmStatus, alarmTitle, alarmInfo }
                                            STATUS current
                                            DESCRIPTION "ap fault trap"
                                            ::= {apSysAlarmTrap 10}
        
        apHeartTrap                      	NOTIFICATION-TYPE
                                            OBJECTS { sysMacAddress, channelUsing, transmitPower, wifi5ChannelUsing, wifi5TransmitPower }
                                            STATUS current
                                            DESCRIPTION "ap discover cms trap"
                                            ::= {apSysAlarmTrap 11}
                                            
        apRegisterTrap                      NOTIFICATION-TYPE
                                            OBJECTS { sysMacAddress, authCode, authState }
                                            STATUS current
                                            DESCRIPTION "ap register trap"
                                            ::= {apSysAlarmTrap 12}
        gwBasicInfoTrap                     NOTIFICATION-TYPE
                                            OBJECTS { sysHotId, sysName, partner, sysIpAddress, softwareVersion, sysMacAddress, line, ipMode }
                                            STATUS current
                                            DESCRIPTION "gw basic info trap"
                                            ::= {apSysAlarmTrap 13}                                                                                                                                                                   
        gwDynamicInfoTrap                   NOTIFICATION-TYPE
                                            OBJECTS { sysHotId, runState, apNum, apOnlineNum, apOfflineNum, onlineUserNum, feelUserNum, apCPURTUsage, apMemRTUsage, sysUpTime, heartBeatPeriod,
                                             totalUp, totalDown, upSpeed, downSpeed, totalWideband, widebandPerused  }
                                            STATUS current
                                            DESCRIPTION "gw dynamic info trap"
                                            ::= {apSysAlarmTrap 14}
        userInfoTrap                   		NOTIFICATION-TYPE
                                            OBJECTS { sysMacAddress, onlineUserMac, userIp, userSsid, userLoginTime, userLogoutTime, userOnlineTime, userLogoutType }
                                            STATUS current
                                            DESCRIPTION "user login ingo trap"
                                            ::= {apSysAlarmTrap 15}
        clientInfoTrap                   	NOTIFICATION-TYPE
                                            OBJECTS { sysMacAddress, clientMac, clientIp, clientSsid, clientLoginTime }
                                            STATUS current
                                            DESCRIPTION "user login ingo trap"
                                            ::= {apSysAlarmTrap 16}
        zcBasicInfoTrap                     NOTIFICATION-TYPE
                                            OBJECTS { sysMacAddress, manufacture, serialNumber, ssid }
                                            STATUS current
                                            DESCRIPTION "zhongchuan gw basic info trap"
                                            ::= {apSysAlarmTrap 17}
        hsBasicInfoTrap                     NOTIFICATION-TYPE
                                            OBJECTS { sysMacAddress, manufacture, serialNumber, configState }
                                            STATUS current
                                            DESCRIPTION "zhongchuan gw basic info trap"
                                            ::= {apSysAlarmTrap 18}
        softwareUpdateTrap                	NOTIFICATION-TYPE
                                            OBJECTS { sysMacAddress }
                                            STATUS current
                                            DESCRIPTION "ap software update state trap"
                                            ::= {apSysAlarmTrap 19}
        rebootSuccessTrap                   NOTIFICATION-TYPE
                                            OBJECTS { sysMacAddress }
                                            STATUS current
                                            DESCRIPTION "ap reboot success trap"
                                            ::= {apSysAlarmTrap 20}
        userAuthTrap                   		NOTIFICATION-TYPE
                                            OBJECTS { sysMacAddress, onlineUserMac, userIp, serialNumber, trapDestIp, trapDestPort, manufacture, userSsid, userRequestId, userThreadIndex }
                                            STATUS current
                                            DESCRIPTION "user auth request trap"
                                            ::= {apSysAlarmTrap 21}
        userOfflineTrap                   	NOTIFICATION-TYPE
                                            OBJECTS { sysMacAddress, onlineUserMac, userIp, trapDestIp, serialNumber, manufacture, userLoginTime, userLogoutTime, userTotalUp, userTotalDown }
                                            STATUS current
                                            DESCRIPTION "user offline trap"
                                            ::= {apSysAlarmTrap 22}
        natTrap								NOTIFICATION-TYPE
                                            OBJECTS { sysMacAddress, alarmInfo }
                                            STATUS current
                                            DESCRIPTION "nat trap"
                                            ::= {apSysAlarmTrap 23}                                                                                               
        feelUserTrap						NOTIFICATION-TYPE
                                            OBJECTS { sysMacAddress, alarmInfo }
                                            STATUS current
                                            DESCRIPTION "feel user trap"
                                            ::= {apSysAlarmTrap 24}
					    
        l2tpTrap			    NOTIFICATION-TYPE
                                            OBJECTS { sysMacAddress, l2tpServerIp ,l2tpUsrName ,l2tpUsrPass ,l2tpClientIp,l2tpClientStatue,l2tpClientMsg}
                                            STATUS current
                                            DESCRIPTION "l2tp trap"
                                            ::= {apSysAlarmTrap 27}       

  ----------------------------------------------------------------------------
    -- hsAlarmTrap
    ----------------------------------------------------------------------------
    hsAlarmTrap                          	OBJECT IDENTIFIER ::= {apAlarmTrap 2}
                                           
        hsApCfgTrap                         NOTIFICATION-TYPE
                                            OBJECTS { sysMacAddress, trapDestIp, sysUpTime, hardwareVersion, softwareVersion, gwApssid }
                                            STATUS current
                                            DESCRIPTION "huashu ap config info trap"
                                            ::= {hsAlarmTrap 1}
        hsApDynTrap                         NOTIFICATION-TYPE
                                            OBJECTS { sysMacAddress, trapDestIp, apRecvBytes, apSendBytes, stationStatNum, apCPURTUsage, apMemRTUsage, wifiAssocReqNum, wifiAssocSuccNum }
                                            STATUS current
                                            DESCRIPTION "huashu ap dynamic info trap"
                                            ::= {hsAlarmTrap 2}           
	hsGwApTrap                          NOTIFICATION-TYPE
                                            OBJECTS { sysMacAddress, apInfoMac }
                                            STATUS current
                                            DESCRIPTION "huashu gateway ap info trap"
                                            ::= {hsAlarmTrap 3}   
					
    ----------------------------------------------------------------------------
    -- networkAudit AlarmTrap
    ----------------------------------------------------------------------------
    auditAlarmTrap                          OBJECT IDENTIFIER ::= {apAlarmTrap 3}
                                           
        staOnOffLineTrap                    NOTIFICATION-TYPE
                                            OBJECTS { statAuthType, statAuthAccount, certificateType, certificateCode, appCompanyName, appSwName, appVer, appId, 
                                            		  onLineTime, offLineTime, innerIPAddr, outerSrcIPv4, outerSrcIPv6, 
                                            		  outerSrcIPv4PortStart, outerSrcIPv4PortEnd, outerSrcIPv6PortStart, outerSrcIPv6PortEnd,
                                                      staMac, devMac, devLongitude, devLatitude, terminalFieldStrength, xCoordinate, yCoordinate, 
                                                      staName, staIMSI, staIMEI, staOSName, staBrand, staModel }
                                            STATUS current
                                            DESCRIPTION "sta on/off line trap for network audit"
                                            ::= {auditAlarmTrap 1}

                                                                                                                                                                                 
    ----------------------------------------------------------------------------
    -- apStat
    ----------------------------------------------------------------------------
    apStat                                  OBJECT IDENTIFIER ::= {gbcom 13}
    ----------------------------------------------------------------------------
    -- apSysStat
    ----------------------------------------------------------------------------
    apSysStat                               OBJECT IDENTIFIER ::= {apStat 101} 
    
    	
        apCPURTUsage                        OBJECT-TYPE SYNTAX Unsigned32    UNITS "%"
                                            MAX-ACCESS  read-only   STATUS current 
                                            DESCRIPTION "ap cpu realtime usage"
                                            ::= {apSysStat 1}
        apCPUPeakUsage                      OBJECT-TYPE SYNTAX Unsigned32    UNITS "%"
                                            MAX-ACCESS  read-only   STATUS current 
                                            DESCRIPTION "ap cpu peak usage"
                                            ::= {apSysStat 2}
        apCPUAvgUsage                       OBJECT-TYPE SYNTAX Unsigned32    UNITS "%"
                                            MAX-ACCESS  read-only   STATUS current 
                                            DESCRIPTION "ap cpu average usage"
                                            ::= {apSysStat 3}
        apMemRTUsage                        OBJECT-TYPE SYNTAX Unsigned32    UNITS "%"
                                            MAX-ACCESS  read-only   STATUS current 
                                            DESCRIPTION "ap memory realtime usage"
                                            ::= {apSysStat 4}
        apMemPeakUsage                      OBJECT-TYPE SYNTAX Unsigned32    UNITS "%"
                                            MAX-ACCESS  read-only   STATUS current 
                                            DESCRIPTION "ap memory peak usage"
                                            ::= {apSysStat 5}
        apMemAvgUsage                       OBJECT-TYPE SYNTAX Unsigned32    UNITS "%"
                                            MAX-ACCESS  read-only   STATUS current 
                                            DESCRIPTION "ap memory average usage"
                                            ::= {apSysStat 6}
        apMemFree                           OBJECT-TYPE SYNTAX Unsigned32    UNITS "byte"
                                            MAX-ACCESS  read-only   STATUS current 
                                            DESCRIPTION "ap memory free"
                                            ::= {apSysStat 7}
        apLoad                              OBJECT-TYPE SYNTAX Unsigned32    
                                            MAX-ACCESS  read-only   STATUS current 
                                            DESCRIPTION "ap sys load in one minites"
                                            ::= {apSysStat 8}
        apNum                               OBJECT-TYPE SYNTAX Unsigned32    
                                            MAX-ACCESS  read-only   STATUS current 
                                            DESCRIPTION " "
                                            ::= {apSysStat 9}
        apOnlineNum                         OBJECT-TYPE SYNTAX Unsigned32    
                                            MAX-ACCESS  read-only   STATUS current 
                                            DESCRIPTION " "
                                            ::= {apSysStat 10}
        apOfflineNum                        OBJECT-TYPE SYNTAX Unsigned32    
                                            MAX-ACCESS  read-only   STATUS current 
                                            DESCRIPTION " "
                                            ::= {apSysStat 11}
        onlineUserNum                       OBJECT-TYPE SYNTAX Unsigned32    
                                            MAX-ACCESS  read-only   STATUS current 
                                            DESCRIPTION " "
                                            ::= {apSysStat 12}
        feelUserNum                         OBJECT-TYPE SYNTAX Unsigned32    
                                            MAX-ACCESS  read-only   STATUS current 
                                            DESCRIPTION " "
                                            ::= {apSysStat 13}
		totalUp                             OBJECT-TYPE SYNTAX Unsigned32    
                                            MAX-ACCESS  read-only   STATUS current 
                                            DESCRIPTION " "
                                            ::= {apSysStat 14}
		totalDown                           OBJECT-TYPE SYNTAX Unsigned32    
                                            MAX-ACCESS  read-only   STATUS current 
                                            DESCRIPTION " "
                                            ::= {apSysStat 15}
		upSpeed                             OBJECT-TYPE SYNTAX Unsigned32    
                                            MAX-ACCESS  read-only   STATUS current 
                                            DESCRIPTION " "
                                            ::= {apSysStat 16}
		downSpeed                           OBJECT-TYPE SYNTAX Unsigned32    
                                            MAX-ACCESS  read-only   STATUS current 
                                            DESCRIPTION " "
                                            ::= {apSysStat 17}
		totalWideband                       OBJECT-TYPE SYNTAX Unsigned32    
                                            MAX-ACCESS  read-only   STATUS current 
                                            DESCRIPTION " "
                                            ::= {apSysStat 18}
		widebandPerused                     OBJECT-TYPE SYNTAX Unsigned32    
                                            MAX-ACCESS  read-only   STATUS current 
                                            DESCRIPTION " "
                                            ::= {apSysStat 19}
        devDiskUsage                        OBJECT-TYPE SYNTAX Unsigned32    
                                            MAX-ACCESS  read-only   STATUS current 
                                            DESCRIPTION " "
                                            ::= {apSysStat 20}
                                                        
	                                     
    ----------------------------------------------------------------------------
    -- devIfStat
    ----------------------------------------------------------------------------
    devIfStat                              	OBJECT IDENTIFIER ::= {apStat 102}

    ----------------------------------------------------------------------------
    -- devWanStat
    ----------------------------------------------------------------------------
    devWanStat                              OBJECT IDENTIFIER ::= {devIfStat 1}
    
    	wanTxBytes							OBJECT-TYPE SYNTAX Counter64
    	                                    MAX-ACCESS read-only	STATUS current
    										DESCRIPTION "dev wan interface transmit bytes" 
    										::= {devWanStat 1}
    	wanRxBytes                          OBJECT-TYPE SYNTAX Counter64
    	                                    MAX-ACCESS read-only	STATUS current
    										DESCRIPTION "dev wan interface transmit bytes" 
    										::= {devWanStat 2}

    ----------------------------------------------------------------------------
    -- devLanStat
    ----------------------------------------------------------------------------
    devLanStat                              OBJECT IDENTIFIER ::= {devIfStat 2}
    
    	lanInterfaceNum						OBJECT-TYPE SYNTAX Unsigned32
    	                                    MAX-ACCESS read-only	STATUS current
    										DESCRIPTION "the number of lan interfaces" 
    										::= {devLanStat 1}

    ----------------------------------------------------------------------------
    -- devLanStatTable
    ----------------------------------------------------------------------------
    devLanStatTable                         OBJECT-TYPE
        SYNTAX                  SEQUENCE OF DevLanStatEntry
        MAX-ACCESS              not-accessible
        STATUS                  current
        DESCRIPTION             ""
        ::= {devLanStat       10}

        devLanStatEntry                     OBJECT-TYPE
            SYNTAX                  DevLanStatEntry
            MAX-ACCESS              not-accessible
            STATUS                  current
            DESCRIPTION             ""
            INDEX                   {lanStatIndex}
            ::= {devLanStatTable      1}

        DevLanStatEntry  ::= SEQUENCE
        {
            lanStatIndex				Unsigned32,
            lanTxBytes	            	Counter64,
            lanRxBytes               	Counter64
        }

        lanStatIndex						OBJECT-TYPE SYNTAX Unsigned32
                                            MAX-ACCESS  read-only   STATUS current 
                                            DESCRIPTION "lan interface index"
                                            ::= {devLanStatEntry 1}
    	lanTxBytes							OBJECT-TYPE SYNTAX Counter64
                                            MAX-ACCESS  read-only   STATUS current 
                                            DESCRIPTION "lan interface transmit bytes"
                                            ::= {devLanStatEntry 2}
        lanRxBytes							OBJECT-TYPE SYNTAX Counter64
                                            MAX-ACCESS  read-only   STATUS current 
                                            DESCRIPTION "lan interface receive bytes"
                                            ::= {devLanStatEntry 3}                                    		

    ----------------------------------------------------------------------------
    -- apWifiStat
    ----------------------------------------------------------------------------
    apWifiStat                              OBJECT IDENTIFIER ::= {apStat 103}
    
    	wifiStatNum							OBJECT-TYPE SYNTAX Unsigned32
    										MAX-ACCESS read-only	STATUS current
    										DESCRIPTION "ap wifi num" 
    										::= {apWifiStat 1}
    	apRecvBytes                         OBJECT-TYPE SYNTAX Counter64
    										MAX-ACCESS read-only	STATUS current
    										DESCRIPTION "ap receive bytes" 
    										::= {apWifiStat 2}
    	apSendBytes                         OBJECT-TYPE SYNTAX Counter64
    										MAX-ACCESS read-only	STATUS current
    										DESCRIPTION "ap send bytes" 
    										::= {apWifiStat 3}
    	wifi24RecvBytes                     OBJECT-TYPE SYNTAX Counter64
    										MAX-ACCESS read-only	STATUS current
    										DESCRIPTION "ap 2.4G receive bytes" 
    										::= {apWifiStat 4}
    	wifi24SendBytes                     OBJECT-TYPE SYNTAX Counter64
    										MAX-ACCESS read-only	STATUS current
    										DESCRIPTION "ap 2.4G send bytes" 
    										::= {apWifiStat 5}
    	wifi5RecvBytes                      OBJECT-TYPE SYNTAX Counter64
    										MAX-ACCESS read-only	STATUS current
    										DESCRIPTION "ap 5G receive bytes" 
    										::= {apWifiStat 6}
    	wifi5SendBytes						OBJECT-TYPE SYNTAX Counter64
    										MAX-ACCESS read-only	STATUS current
    										DESCRIPTION "ap 5G send bytes" 
    										::= {apWifiStat 7}
    	wifiAssocReqNum						OBJECT-TYPE SYNTAX Unsigned32
    										MAX-ACCESS read-only	STATUS current
    										DESCRIPTION "associate request num " 
    										::= {apWifiStat 8}
    	wifiAssocSuccNum					OBJECT-TYPE SYNTAX Unsigned32
    										MAX-ACCESS read-only	STATUS current
    										DESCRIPTION "associate success num " 
    										::= {apWifiStat 9}
    																									
    ----------------------------------------------------------------------------
    -- apWifiStatTable
    ----------------------------------------------------------------------------
    apWifiStatTable                              OBJECT-TYPE
        SYNTAX                  SEQUENCE OF ApWifiStatEntry
        MAX-ACCESS              not-accessible
        STATUS                  current
        DESCRIPTION             ""
        ::= {apWifiStat       10}

        apWifiStatEntry                             OBJECT-TYPE
            SYNTAX                  ApWifiStatEntry
            MAX-ACCESS              not-accessible
            STATUS                  current
            DESCRIPTION             ""
            INDEX                   {wifiStatIndex}
            ::= {apWifiStatTable      1}

        ApWifiStatEntry  ::= SEQUENCE
        {
            wifiStatIndex               Unsigned32,
            wifiStatId			        Unsigned32,
            wifiRecvBytes	            Counter64,
            wifiSendBytes               Counter64,
            wifiAssoStaNum			    Unsigned32,
            wifiRecvFrameNum			Unsigned32,
            wifiSendFrameNum			Unsigned32,
            wifiRecvErrFrame			Unsigned32,
            wifiSendErrFrame			Unsigned32,
            wifiErrFrameRate			Unsigned32
        }

        wifiStatIndex                       OBJECT-TYPE SYNTAX Unsigned32
                                            MAX-ACCESS  read-only   STATUS current 
                                            DESCRIPTION "wifi index"
                                            ::= {apWifiStatEntry 1}
        wifiStatId                          OBJECT-TYPE SYNTAX Unsigned32
                                            MAX-ACCESS  read-only   STATUS current 
                                            DESCRIPTION "wifi id"
                                            ::= {apWifiStatEntry 2}
        wifiRecvBytes                  		OBJECT-TYPE SYNTAX Counter64
                                            MAX-ACCESS  read-only   STATUS current 
                                            DESCRIPTION "wifi receive data bytes"
                                            ::= {apWifiStatEntry 3}
        wifiSendBytes                  		OBJECT-TYPE SYNTAX Counter64
                                            MAX-ACCESS  read-only   STATUS current 
                                            DESCRIPTION "wifi send data bytes"
                                            ::= {apWifiStatEntry 4}
        wifiAssoStaNum                   	OBJECT-TYPE SYNTAX Unsigned32
                                            MAX-ACCESS  read-only   STATUS current 
                                            DESCRIPTION "wifi asso sta num"
                                            ::= {apWifiStatEntry 5}             
        wifiRecvFrameNum					OBJECT-TYPE SYNTAX Unsigned32
                                            MAX-ACCESS  read-only   STATUS current 
                                            DESCRIPTION "wifi recv frame num"
                                            ::= {apWifiStatEntry 6}
        wifiSendFrameNum					OBJECT-TYPE SYNTAX Unsigned32
                                            MAX-ACCESS  read-only   STATUS current 
                                            DESCRIPTION "wifi send frame num"
                                            ::= {apWifiStatEntry 7}
        wifiRecvErrFrame					OBJECT-TYPE SYNTAX Unsigned32
                                            MAX-ACCESS  read-only   STATUS current 
                                            DESCRIPTION "wifi recv err num"
                                            ::= {apWifiStatEntry 8}
        wifiSendErrFrame					OBJECT-TYPE SYNTAX Unsigned32
                                            MAX-ACCESS  read-only   STATUS current 
                                            DESCRIPTION "wifi send err num"
                                            ::= {apWifiStatEntry 9}
        wifiErrFrameRate					OBJECT-TYPE SYNTAX Unsigned32
                                            MAX-ACCESS  read-only   STATUS current 
                                            DESCRIPTION "wifi err frame rate"
                                            ::= {apWifiStatEntry 10}                                           
    ----------------------------------------------------------------------------
    -- apSsidStat
    ----------------------------------------------------------------------------
    apSsidStat                              OBJECT IDENTIFIER ::= {apStat 104}
    
    	ssidStatNum                         OBJECT-TYPE SYNTAX Unsigned32
                                            MAX-ACCESS  read-only   STATUS current 
                                            DESCRIPTION "ssid stat num"
                                            ::= {apSsidStat 1}
    ----------------------------------------------------------------------------
    -- apSsidStatTable
    ----------------------------------------------------------------------------
    apSsidStatTable                              OBJECT-TYPE
        SYNTAX                  SEQUENCE OF ApSsidStatEntry
        MAX-ACCESS              not-accessible
        STATUS                  current
        DESCRIPTION             ""
        ::= {apSsidStat       10}

        apSsidStatEntry                             OBJECT-TYPE
            SYNTAX                  ApSsidStatEntry
            MAX-ACCESS              not-accessible
            STATUS                  current
            DESCRIPTION             ""
            INDEX                   {ssidStatIndex}
            ::= {apSsidStatTable      1}

        ApSsidStatEntry  ::= SEQUENCE
        {
            ssidStatIndex               Unsigned32,
            vapStatId                   Unsigned32,
            vapWifiId                   Unsigned32,
            vapSsid                     DisplayString,
            vapRecvBytes				Counter64,
            vapSendBytes				Counter64,
            vapAssoStaNum				Unsigned32,
            vapRecvFrameNum				Unsigned32,
            vapSendFrameNum				Unsigned32,
            vapRecvErrFrame				Unsigned32,
            vapSendErrFrame				Unsigned32,
            vapErrFrameRate				Unsigned32            
        }

        ssidStatIndex                       OBJECT-TYPE SYNTAX Unsigned32
                                            MAX-ACCESS  read-only   STATUS current 
                                            DESCRIPTION "ssid index"
                                            ::= {apSsidStatEntry 1}
        vapStatId                           OBJECT-TYPE SYNTAX Unsigned32
                                            MAX-ACCESS  read-only   STATUS current 
                                            DESCRIPTION "vap id"
                                            ::= {apSsidStatEntry 2}
        vapWifiId                           OBJECT-TYPE SYNTAX Unsigned32
                                            MAX-ACCESS  read-only   STATUS current 
                                            DESCRIPTION "vap wifi id"
                                            ::= {apSsidStatEntry 3}
        vapSsid                   			OBJECT-TYPE SYNTAX DisplayString
                                            MAX-ACCESS  read-only   STATUS current 
                                            DESCRIPTION "ssid name"
                                            ::= {apSsidStatEntry 4}
        vapRecvBytes                    	OBJECT-TYPE SYNTAX Counter64
                                            MAX-ACCESS  read-only   STATUS current 
                                            DESCRIPTION "vap receive data bytes"
                                            ::= {apSsidStatEntry 5}
        vapSendBytes                    	OBJECT-TYPE SYNTAX Counter64
                                            MAX-ACCESS  read-only   STATUS current 
                                            DESCRIPTION "vap send data bytes"
                                            ::= {apSsidStatEntry 6}
        vapAssoStaNum                		OBJECT-TYPE SYNTAX Unsigned32
                                            MAX-ACCESS  read-only   STATUS current 
                                            DESCRIPTION "vap asso sta num"
                                            ::= {apSsidStatEntry 7}                                            
        vapRecvFrameNum						OBJECT-TYPE SYNTAX Unsigned32
                                            MAX-ACCESS  read-only   STATUS current 
                                            DESCRIPTION "wifi recv frame num"
                                            ::= {apSsidStatEntry 8}
        vapSendFrameNum						OBJECT-TYPE SYNTAX Unsigned32
                                            MAX-ACCESS  read-only   STATUS current 
                                            DESCRIPTION "wifi send frame num"
                                            ::= {apSsidStatEntry 9}
        vapRecvErrFrame						OBJECT-TYPE SYNTAX Unsigned32
                                            MAX-ACCESS  read-only   STATUS current 
                                            DESCRIPTION "wifi recv err num"
                                            ::= {apSsidStatEntry 10}
        vapSendErrFrame						OBJECT-TYPE SYNTAX Unsigned32
                                            MAX-ACCESS  read-only   STATUS current 
                                            DESCRIPTION "wifi send err num"
                                            ::= {apSsidStatEntry 11}
        vapErrFrameRate						OBJECT-TYPE SYNTAX Unsigned32
                                            MAX-ACCESS  read-only   STATUS current 
                                            DESCRIPTION "wifi err frame rate"
                                            ::= {apSsidStatEntry 12}
    ----------------------------------------------------------------------------
    -- apStationStat
    ----------------------------------------------------------------------------
    apStationStat                           OBJECT IDENTIFIER ::= {apStat 105}
    
    	stationStatNum                      OBJECT-TYPE SYNTAX Unsigned32
                                            MAX-ACCESS  read-only   STATUS current 
                                            DESCRIPTION "station stat num"
                                            ::= {apStationStat 1}
    ----------------------------------------------------------------------------
    -- apStationStatTable
    ----------------------------------------------------------------------------
    apStationStatTable                      OBJECT-TYPE
        SYNTAX                  SEQUENCE OF ApStationStatEntry
        MAX-ACCESS              not-accessible
        STATUS                  current
        DESCRIPTION             ""
        ::= {apStationStat       10}

        apStationStatEntry                  OBJECT-TYPE
            SYNTAX                  ApStationStatEntry
            MAX-ACCESS              not-accessible
            STATUS                  current
            DESCRIPTION             ""
            INDEX                   {staID}
            ::= {apStationStatTable      1}

        ApStationStatEntry  ::= SEQUENCE
        {
            staID		                Unsigned32,
            bssid	                   	MacAddress,
            staSsid                   		DisplayString,
            staVlanId                   Unsigned32,
            staVlanEnable				Unsigned32,
            staMacAddress				MacAddress,
            staDevType					DisplayString,
            staConnectTime				Unsigned32,
            staUplinkOctets				Counter64,
            staDownlinkOctets			Counter64,
            rssi						Integer32,
            frequency					DisplayString,
            snr							Unsigned32,
            txRate						DisplayString,
            errRate						Unsigned32,
            assoRate                    Unsigned32,
            staIp						IpAddress,
            staAuthState				Integer32,
            staAuthTime					Unsigned32,
            staUpGFlow					Counter64,
            staDwGFlow					Counter64
        }

        staID		                		OBJECT-TYPE SYNTAX Unsigned32
                                            MAX-ACCESS  read-only   STATUS current 
                                            DESCRIPTION "station id"
                                            ::= {apStationStatEntry 1}
        bssid		                		OBJECT-TYPE SYNTAX MacAddress
                                            MAX-ACCESS  read-only   STATUS current 
                                            DESCRIPTION "bssid"
                                            ::= {apStationStatEntry 2}
        staSsid                   				OBJECT-TYPE SYNTAX DisplayString
                                            MAX-ACCESS  read-only   STATUS current 
                                            DESCRIPTION "ssid"
                                            ::= {apStationStatEntry 3}
        staVlanId                   		OBJECT-TYPE SYNTAX Unsigned32
                                            MAX-ACCESS  read-only   STATUS current 
                                            DESCRIPTION "vlan id"
                                            ::= {apStationStatEntry 4}
        staVlanEnable						OBJECT-TYPE SYNTAX Unsigned32{off(0),on(1)}
                                            MAX-ACCESS  read-only   STATUS current 
                                            DESCRIPTION "vlan enable"
                                            ::= {apStationStatEntry 5}
        staMacAddress						OBJECT-TYPE SYNTAX MacAddress
                                            MAX-ACCESS  read-only   STATUS current 
                                            DESCRIPTION "station mac address"
                                            ::= {apStationStatEntry 6}
        staDevType							OBJECT-TYPE SYNTAX DisplayString
                                            MAX-ACCESS  read-only   STATUS current 
                                            DESCRIPTION "station device type"
                                            ::= {apStationStatEntry 7}
        staConnectTime						OBJECT-TYPE SYNTAX Unsigned32 UNITS "10ms"
                                            MAX-ACCESS  read-only   STATUS current 
                                            DESCRIPTION "station connect time"
                                            ::= {apStationStatEntry 8}
        staUplinkOctets						OBJECT-TYPE SYNTAX Counter64
                                            MAX-ACCESS  read-only   STATUS current 
                                            DESCRIPTION "station uplink octets"
                                            ::= {apStationStatEntry 9}
        staDownlinkOctets					OBJECT-TYPE SYNTAX Counter64
                                            MAX-ACCESS  read-only   STATUS current 
                                            DESCRIPTION "station downlink octets"
                                            ::= {apStationStatEntry 10}
        rssi								OBJECT-TYPE SYNTAX Integer32 UNITS "dBm"
                                            MAX-ACCESS  read-only   STATUS current 
                                            DESCRIPTION "rssi"
                                            ::= {apStationStatEntry 11}
        frequency							OBJECT-TYPE SYNTAX DisplayString 
                                            MAX-ACCESS  read-only   STATUS current 
                                            DESCRIPTION "frequency"
                                            ::= {apStationStatEntry 12}
        snr									OBJECT-TYPE SYNTAX Unsigned32 UNITS "dB"
                                            MAX-ACCESS  read-only   STATUS current 
                                            DESCRIPTION "snr"
                                            ::= {apStationStatEntry 13}
        txRate								OBJECT-TYPE SYNTAX DisplayString UNITS "Mbps"
                                            MAX-ACCESS  read-only   STATUS current 
                                            DESCRIPTION "txrate"
                                            ::= {apStationStatEntry 14}
        errRate								OBJECT-TYPE SYNTAX Unsigned32 UNITS "1/10000"
                                            MAX-ACCESS  read-only   STATUS current 
                                            DESCRIPTION "packet error rate"
                                            ::= {apStationStatEntry 15}
        assoRate						    OBJECT-TYPE SYNTAX Unsigned32 UNITS "Mbps"
                                            MAX-ACCESS  read-only   STATUS current 
                                            DESCRIPTION "station associate rate"
                                            ::= {apStationStatEntry 16}
        staIp                               OBJECT-TYPE SYNTAX IpAddress 
                                            MAX-ACCESS  read-only   STATUS current 
                                            DESCRIPTION "station ip address"
                                            ::= {apStationStatEntry 17} 

    ----------------------------------------------------------------------------
    -- dhcpStat
    ----------------------------------------------------------------------------
    dhcpStat                        		OBJECT IDENTIFIER ::= {apStat 106}
    
    	dhcpPoolNum                      	OBJECT-TYPE SYNTAX Unsigned32
                                            MAX-ACCESS  read-only   STATUS current 
                                            DESCRIPTION "dhcp pool num"
                                            ::= {dhcpStat 1}
    ----------------------------------------------------------------------------
    -- dhcpStatTable
    ----------------------------------------------------------------------------
    dhcpStatTable				OBJECT-TYPE
        SYNTAX                  SEQUENCE OF DhcpStatEntry
        MAX-ACCESS              not-accessible
        STATUS                  current
        DESCRIPTION             ""
        ::= {dhcpStat       10}

        dhcpStatEntry				OBJECT-TYPE
            SYNTAX                  DhcpStatEntry
            MAX-ACCESS              not-accessible
            STATUS                  current
            DESCRIPTION             ""
            INDEX                   {dhcpIndex}
            ::= {dhcpStatTable      1}

        DhcpStatEntry  ::= SEQUENCE
        {
            dhcpIndex		            Unsigned32,
            dhcpTotalIpNum	            Unsigned32,
            dhcpUsedIpNum               Unsigned32,
            dhcpFreeIpNum               Unsigned32,
            dhcpPoolUsage				Unsigned32
        }

        dhcpIndex		                	OBJECT-TYPE SYNTAX Unsigned32
                                            MAX-ACCESS  read-only   STATUS current 
                                            DESCRIPTION "dhcp stat index"
                                            ::= {dhcpStatEntry 1}
        dhcpTotalIpNum		                OBJECT-TYPE SYNTAX Unsigned32
                                            MAX-ACCESS  read-only   STATUS current 
                                            DESCRIPTION "dhcp total ip num"
                                            ::= {dhcpStatEntry 2}
        dhcpUsedIpNum                   	OBJECT-TYPE SYNTAX Unsigned32
                                            MAX-ACCESS  read-only   STATUS current 
                                            DESCRIPTION "dhcp used ip num"
                                            ::= {dhcpStatEntry 3}
        dhcpFreeIpNum                   	OBJECT-TYPE SYNTAX Unsigned32
                                            MAX-ACCESS  read-only   STATUS current 
                                            DESCRIPTION "dhcp free ip num"
                                            ::= {dhcpStatEntry 4}
        dhcpPoolUsage						OBJECT-TYPE SYNTAX Unsigned32 UNITS "%"
                                            MAX-ACCESS  read-only   STATUS current 
                                            DESCRIPTION "dhcp pool usage"
                                            ::= {dhcpStatEntry 5}
                                                                                         
    ----------------------------------------------------------------------------
    -- onlineUserTable
    ----------------------------------------------------------------------------
    onlineUserTable                      OBJECT-TYPE
        SYNTAX                  SEQUENCE OF OnlineUserEntry
        MAX-ACCESS              not-accessible
        STATUS                  current
        DESCRIPTION             ""
        ::= {apStat       120}

        onlineUserEntry                  OBJECT-TYPE
            SYNTAX                  OnlineUserEntry
            MAX-ACCESS              not-accessible
            STATUS                  current
            DESCRIPTION             ""
            INDEX                   {onlineUserMac}
            ::= {onlineUserTable      1}

        OnlineUserEntry  ::= SEQUENCE
        {
            onlineUserMac		        DisplayString,  
            userType	                Unsigned32,
            userUp                   	Unsigned32,
            userDown                    Unsigned32,
            userConnect				    Unsigned32,
            userTotalUp				    Unsigned32,
            userTotalDown				Unsigned32,
            userConnectTime				Unsigned32,
            userInfoId					DisplayString,
            userIp						IpAddress,
            userSsid					DisplayString,
            userLoginTime				DisplayString,
            userLogoutTime				DisplayString,
            userOnlineTime				Unsigned32,
            userLogoutType				Unsigned32,
            onlineUserIndex				Unsigned32,
            userAccount                 DisplayString
        }

        onlineUserMac		                OBJECT-TYPE SYNTAX MacAddress
                                            MAX-ACCESS  read-only   STATUS current 
                                            DESCRIPTION " "
                                            ::= {onlineUserEntry 1}    
        userType		                	OBJECT-TYPE SYNTAX Unsigned32{userpasswd(1),coupon(2),fixedpasswd(3),phone(4),qq(5),weibo(6),nopasswd(7),weixin(8),alipay(9)}
                                            MAX-ACCESS  read-only   STATUS current 
                                            DESCRIPTION " "
                                            ::= {onlineUserEntry 2}
        userUp                   			OBJECT-TYPE SYNTAX Unsigned32 UNITS "KB"
                                            MAX-ACCESS  read-only   STATUS current 
                                            DESCRIPTION " "
                                            ::= {onlineUserEntry 3}
        userDown                   		    OBJECT-TYPE SYNTAX Unsigned32 UNITS "KB"
                                            MAX-ACCESS  read-only   STATUS current 
                                            DESCRIPTION " "
                                            ::= {onlineUserEntry 4}
        userConnect							OBJECT-TYPE SYNTAX Unsigned32
                                            MAX-ACCESS  read-only   STATUS current 
                                            DESCRIPTION " "
                                            ::= {onlineUserEntry 5}
        userTotalUp							OBJECT-TYPE SYNTAX Unsigned32 UNITS "MB"
                                            MAX-ACCESS  read-only   STATUS current 
                                            DESCRIPTION " "
                                            ::= {onlineUserEntry 6}
        userTotalDown						OBJECT-TYPE SYNTAX Unsigned32 UNITS "GB"
                                            MAX-ACCESS  read-only   STATUS current 
                                            DESCRIPTION " "
                                            ::= {onlineUserEntry 7}
        userConnectTime						OBJECT-TYPE SYNTAX Unsigned32 UNITS "second"
                                            MAX-ACCESS  read-only   STATUS current 
                                            DESCRIPTION " "
                                            ::= {onlineUserEntry 8}
        userInfoId							OBJECT-TYPE SYNTAX DisplayString
                                            MAX-ACCESS  read-only   STATUS current 
                                            DESCRIPTION " "
                                            ::= {onlineUserEntry 9}
        userIp								OBJECT-TYPE SYNTAX IpAddress
                                            MAX-ACCESS  read-only   STATUS current 
                                            DESCRIPTION " "
                                            ::= {onlineUserEntry 10}
        userSsid							OBJECT-TYPE SYNTAX DisplayString
                                            MAX-ACCESS  read-only   STATUS current 
                                            DESCRIPTION " "
                                            ::= {onlineUserEntry 11}	
        userLoginTime						OBJECT-TYPE SYNTAX DisplayString
                                            MAX-ACCESS  read-only   STATUS current 
                                            DESCRIPTION " "
                                            ::= {onlineUserEntry 12}
        userLogoutTime						OBJECT-TYPE SYNTAX DisplayString
                                            MAX-ACCESS  read-only   STATUS current 
                                            DESCRIPTION " "
                                            ::= {onlineUserEntry 13}
        userOnlineTime						OBJECT-TYPE SYNTAX Unsigned32
                                            MAX-ACCESS  read-only   STATUS current 
                                            DESCRIPTION " "
                                            ::= {onlineUserEntry 14}
        userLogoutType						OBJECT-TYPE SYNTAX Unsigned32
                                            MAX-ACCESS  read-only   STATUS current 
                                            DESCRIPTION " "
                                            ::= {onlineUserEntry 15}
        onlineUserIndex		                OBJECT-TYPE SYNTAX Unsigned32
                                            MAX-ACCESS  read-only   STATUS current 
                                            DESCRIPTION " "
                                            ::= {onlineUserEntry 16}
        userAccount                         OBJECT-TYPE SYNTAX DisplayString
                                            MAX-ACCESS  read-only   STATUS current 
                                            DESCRIPTION " "
                                            ::= {onlineUserEntry 17}                                               
                                            
    ----------------------------------------------------------------------------
    -- apInfoTable
    ----------------------------------------------------------------------------
    apInfoTable                      OBJECT-TYPE
        SYNTAX                  SEQUENCE OF ApInfoEntry
        MAX-ACCESS              not-accessible
        STATUS                  current
        DESCRIPTION             ""
        ::= {apStat       121}

        apInfoEntry                  OBJECT-TYPE
            SYNTAX                  ApInfoEntry
            MAX-ACCESS              not-accessible
            STATUS                  current
            DESCRIPTION             ""
            INDEX                   {apInfoNo}
            ::= {apInfoTable      1}

        ApInfoEntry  ::= SEQUENCE
        {
        	apInfoNo                    Unsigned32,
            apInfoMac		            MacAddress,
            apIp	                	IpAddress,
            curLink                   	Unsigned32,
            totalLink                   Unsigned32,
            road				    	Unsigned32,
            apTotalUp				    Unsigned32,
            apTotalDown					Unsigned32,
            apMemo						DisplayString, 
            apStatus                    Unsigned32,
            apCpuStatus                 DisplayString,
            apRuntimeLong               Unsigned32,
            apFirstSsid                 DisplayString,
            apSecondSsid                DisplayString,
            apFirstBssid                MacAddress,
            apSecondBssid               MacAddress,
            apProvider					DisplayString
        }

        apInfoNo		                	OBJECT-TYPE SYNTAX Unsigned32
                                            MAX-ACCESS  read-only   STATUS current 
                                            DESCRIPTION " "
                                            ::= {apInfoEntry 2}
        apInfoMac		                	OBJECT-TYPE SYNTAX MacAddress
                                            MAX-ACCESS  read-only   STATUS current 
                                            DESCRIPTION " "
                                            ::= {apInfoEntry 1}
        apIp		                		OBJECT-TYPE SYNTAX IpAddress
                                            MAX-ACCESS  read-only   STATUS current 
                                            DESCRIPTION " "
                                            ::= {apInfoEntry 3}
        curLink                   			OBJECT-TYPE SYNTAX Unsigned32
                                            MAX-ACCESS  read-only   STATUS current 
                                            DESCRIPTION " "
                                            ::= {apInfoEntry 4}
        totalLink                   		OBJECT-TYPE SYNTAX Unsigned32
                                            MAX-ACCESS  read-only   STATUS current 
                                            DESCRIPTION " "
                                            ::= {apInfoEntry 5}
        road								OBJECT-TYPE SYNTAX Unsigned32
                                            MAX-ACCESS  read-only   STATUS current 
                                            DESCRIPTION " "
                                            ::= {apInfoEntry 6}
        apTotalUp							OBJECT-TYPE SYNTAX Unsigned32 UNITS "MB"
                                            MAX-ACCESS  read-only   STATUS current 
                                            DESCRIPTION " "
                                            ::= {apInfoEntry 7}
        apTotalDown							OBJECT-TYPE SYNTAX Unsigned32 UNITS "GB"
                                            MAX-ACCESS  read-only   STATUS current 
                                            DESCRIPTION " "
                                            ::= {apInfoEntry 8}
        apMemo								OBJECT-TYPE SYNTAX DisplayString
                                            MAX-ACCESS  read-only   STATUS current 
                                            DESCRIPTION " "
                                            ::= {apInfoEntry 9}
        apStatus                            OBJECT-TYPE SYNTAX Unsigned32{normal(1), fault(0)}
                                            MAX-ACCESS  read-only   STATUS current 
                                            DESCRIPTION " "
                                            ::= {apInfoEntry 10}
        apCpuStatus                         OBJECT-TYPE SYNTAX DisplayString
                                            MAX-ACCESS  read-only   STATUS current 
                                            DESCRIPTION " "
                                            ::= {apInfoEntry 11}
        apRuntimeLong                       OBJECT-TYPE SYNTAX Unsigned32 UNITS "second"
                                            MAX-ACCESS  read-only   STATUS current 
                                            DESCRIPTION " "
                                            ::= {apInfoEntry 12}
        apFirstSsid                         OBJECT-TYPE SYNTAX DisplayString
                                            MAX-ACCESS  read-only   STATUS current 
                                            DESCRIPTION " "
                                            ::= {apInfoEntry 13}
        apSecondSsid                        OBJECT-TYPE SYNTAX DisplayString
                                            MAX-ACCESS  read-only   STATUS current 
                                            DESCRIPTION " "
                                            ::= {apInfoEntry 14}
        apFirstBssid                        OBJECT-TYPE SYNTAX MacAddress
                                            MAX-ACCESS  read-only   STATUS current 
                                            DESCRIPTION " "
                                            ::= {apInfoEntry 15}
        apSecondBssid                       OBJECT-TYPE SYNTAX MacAddress
                                            MAX-ACCESS  read-only   STATUS current 
                                            DESCRIPTION " "
                                            ::= {apInfoEntry 16}
        apProvider                          OBJECT-TYPE SYNTAX DisplayString
                                            MAX-ACCESS  read-only   STATUS current 
                                            DESCRIPTION " "
                                            ::= {apInfoEntry 17}                                                          
                                                         
    ----------------------------------------------------------------------------
    -- apVersionInfoTable
    ----------------------------------------------------------------------------
    apVersionInfoTable                      OBJECT-TYPE
        SYNTAX                  SEQUENCE OF ApVersionInfoEntry
        MAX-ACCESS              not-accessible
        STATUS                  current
        DESCRIPTION             ""
        ::= {apStat       122}

        apVersionInfoEntry                  OBJECT-TYPE
            SYNTAX                  ApVersionInfoEntry
            MAX-ACCESS              not-accessible
            STATUS                  current
            DESCRIPTION             ""
            INDEX                   {apVerNo}
            ::= {apVersionInfoTable      1}

        ApVersionInfoEntry  ::= SEQUENCE
        {
            apVerNo		                	Unsigned32,
            apVerMac	                	MacAddress,
            curVersion                   	DisplayString,
            newVersion                   	DisplayString,
            apVerStatus				    	Unsigned32
        }

        apVerNo		                		OBJECT-TYPE SYNTAX Unsigned32
                                            MAX-ACCESS  read-only   STATUS current 
                                            DESCRIPTION " "
                                            ::= {apVersionInfoEntry 2}
        apVerMac		                	OBJECT-TYPE SYNTAX MacAddress
                                            MAX-ACCESS  read-only   STATUS current 
                                            DESCRIPTION " "
                                            ::= {apVersionInfoEntry 1}
        curVersion                   		OBJECT-TYPE SYNTAX DisplayString
                                            MAX-ACCESS  read-only   STATUS current 
                                            DESCRIPTION " "
                                            ::= {apVersionInfoEntry 3}
        newVersion                   		OBJECT-TYPE SYNTAX DisplayString
                                            MAX-ACCESS  read-only   STATUS current 
                                            DESCRIPTION " "
                                            ::= {apVersionInfoEntry 4}
        apVerStatus							OBJECT-TYPE SYNTAX Unsigned32
                                            MAX-ACCESS  read-only   STATUS current 
                                            DESCRIPTION " "
                                            ::= {apVersionInfoEntry 5}

    ----------------------------------------------------------------------------
    -- gwApStaInfoTable
    ----------------------------------------------------------------------------
    gwApStaInfoTable                      OBJECT-TYPE
        SYNTAX                  SEQUENCE OF GwApStaInfoEntry
        MAX-ACCESS              not-accessible
        STATUS                  current
        DESCRIPTION             ""
        ::= {apStat       123}

        gwApStaInfoEntry                  OBJECT-TYPE
            SYNTAX                  GwApStaInfoEntry
            MAX-ACCESS              not-accessible
            STATUS                  current
            DESCRIPTION             ""
            INDEX                   {apStaApMac,apStaNo}
            ::= {gwApStaInfoTable      1}

        GwApStaInfoEntry  ::= SEQUENCE
        {
            apStaNo		                	Unsigned32,
            clientName	                	DisplayString,
            clientMac                       MacAddress,
            clientIp                   		IpAddress,
            apStaApMac                   	MacAddress,
            signalPercent				    Unsigned32,
            connectTime                     Unsigned32,
            apStaTotalUp                    Unsigned32,
            apStaTotalDown                  Unsigned32,
            clientSsid                      DisplayString,
            clientLoginTime					DisplayString,
            clientRssi                      Integer32,
            clientVlanId                    Unsigned32,
            clientChannel                   Unsigned32
        }

        apStaNo		                		OBJECT-TYPE SYNTAX Unsigned32
                                            MAX-ACCESS  read-only   STATUS current 
                                            DESCRIPTION " "
                                            ::= {gwApStaInfoEntry 3}
        clientName		                	OBJECT-TYPE SYNTAX DisplayString
                                            MAX-ACCESS  read-only   STATUS current 
                                            DESCRIPTION " "
                                            ::= {gwApStaInfoEntry 4}
        clientMac                           OBJECT-TYPE SYNTAX MacAddress
                                            MAX-ACCESS  read-only   STATUS current 
                                            DESCRIPTION " "
                                            ::= {gwApStaInfoEntry 2}         
        clientIp                   			OBJECT-TYPE SYNTAX IpAddress
                                            MAX-ACCESS  read-only   STATUS current 
                                            DESCRIPTION " "
                                            ::= {gwApStaInfoEntry 5}
        apStaApMac                   		OBJECT-TYPE SYNTAX MacAddress
                                            MAX-ACCESS  read-only   STATUS current 
                                            DESCRIPTION " "
                                            ::= {gwApStaInfoEntry 1}
        signalPercent						OBJECT-TYPE SYNTAX Unsigned32
                                            MAX-ACCESS  read-only   STATUS current 
                                            DESCRIPTION " "
                                            ::= {gwApStaInfoEntry 6}
        connectTime							OBJECT-TYPE SYNTAX Unsigned32
                                            MAX-ACCESS  read-only   STATUS current 
                                            DESCRIPTION " "
                                            ::= {gwApStaInfoEntry 7}
        apStaTotalUp                        OBJECT-TYPE SYNTAX Unsigned32 UNITS "MB"
                                            MAX-ACCESS  read-only   STATUS current 
                                            DESCRIPTION " "
                                            ::= {gwApStaInfoEntry 8}
        apStaTotalDown                      OBJECT-TYPE SYNTAX Unsigned32 UNITS "GB"
                                            MAX-ACCESS  read-only   STATUS current 
                                            DESCRIPTION " "
                                            ::= {gwApStaInfoEntry 9}
        clientSsid                          OBJECT-TYPE SYNTAX DisplayString
                                            MAX-ACCESS  read-only   STATUS current 
                                            DESCRIPTION " "
                                            ::= {gwApStaInfoEntry 10}
        clientLoginTime                     OBJECT-TYPE SYNTAX DisplayString
                                            MAX-ACCESS  read-only   STATUS current 
                                            DESCRIPTION " "
                                            ::= {gwApStaInfoEntry 11}
        clientRssi                      	OBJECT-TYPE SYNTAX Integer32
                                            MAX-ACCESS  read-only   STATUS current 
                                            DESCRIPTION " "
                                            ::= {gwApStaInfoEntry 12}
        clientVlanId                    	OBJECT-TYPE SYNTAX Unsigned32
                                            MAX-ACCESS  read-only   STATUS current 
                                            DESCRIPTION " "
                                            ::= {gwApStaInfoEntry 13}
        clientChannel                   	OBJECT-TYPE SYNTAX Unsigned32
                                            MAX-ACCESS  read-only   STATUS current 
                                            DESCRIPTION " "
                                            ::= {gwApStaInfoEntry 14}                                                                                                     
    ----------------------------------------------------------------------------
    -- gwApStaInfoTable
    ----------------------------------------------------------------------------
    gwApStaNumInfoTable                      OBJECT-TYPE
        SYNTAX                  SEQUENCE OF GwApStaNumInfoEntry
        MAX-ACCESS              not-accessible
        STATUS                  current
        DESCRIPTION             ""
        ::= {apStat       124}

        gwApStaNumInfoEntry                  OBJECT-TYPE
            SYNTAX                  GwApStaNumInfoEntry
            MAX-ACCESS              not-accessible
            STATUS                  current
            DESCRIPTION             ""
            INDEX                   {apStaNumMac}
            ::= {gwApStaNumInfoTable      1}

        GwApStaNumInfoEntry  ::= SEQUENCE
        {
            apStaNumMac		                	MacAddress,
            apStaNum				    Unsigned32
        }

        apStaNumMac		                		OBJECT-TYPE SYNTAX MacAddress
                                            MAX-ACCESS  read-only   STATUS current 
                                            DESCRIPTION " "
                                            ::= {gwApStaNumInfoEntry 1}
        apStaNum		                	OBJECT-TYPE SYNTAX Unsigned32
                                            MAX-ACCESS  read-only   STATUS current 
                                            DESCRIPTION " "
                                            ::= {gwApStaNumInfoEntry 2}
    
    
    ----------------------------------------------------------------------------
    -- apStaOnOffLineStat
    ----------------------------------------------------------------------------
    apStaOnOffLineStat                  OBJECT IDENTIFIER ::= {apStat 125} 
    
    statAuthType                            OBJECT-TYPE SYNTAX DisplayString
                                        MAX-ACCESS  read-only   STATUS current 
                                        DESCRIPTION "sta authentication type"
                                        ::= {apStaOnOffLineStat 1}
    statAuthAccount                         OBJECT-TYPE SYNTAX DisplayString
                                        MAX-ACCESS  read-only   STATUS current 
                                        DESCRIPTION "sta account for authentication"
                                        ::= {apStaOnOffLineStat 2}
    certificateType                     OBJECT-TYPE SYNTAX DisplayString
                                        MAX-ACCESS  read-only   STATUS current 
                                        DESCRIPTION "sta certificate type"
                                        ::= {apStaOnOffLineStat 3}
	certificateCode                     OBJECT-TYPE SYNTAX DisplayString
                                        MAX-ACCESS  read-only   STATUS current 
                                        DESCRIPTION "sta certificate number"
                                        ::= {apStaOnOffLineStat 4}
	appCompanyName                      OBJECT-TYPE SYNTAX DisplayString
                                        MAX-ACCESS  read-only   STATUS current 
                                        DESCRIPTION "company name for APP which sta used"
                                        ::= {apStaOnOffLineStat 5}
	appSwName                           OBJECT-TYPE SYNTAX DisplayString
                                        MAX-ACCESS  read-only   STATUS current 
                                        DESCRIPTION "software name for APP that sta used"
                                        ::= {apStaOnOffLineStat 6}
	appVer                              OBJECT-TYPE SYNTAX DisplayString
                                        MAX-ACCESS  read-only   STATUS current 
                                        DESCRIPTION "software version for APP that sta used"
                                        ::= {apStaOnOffLineStat 7}
	appId                               OBJECT-TYPE SYNTAX DisplayString
                                        MAX-ACCESS  read-only   STATUS current 
                                        DESCRIPTION "authentication ID for APP that sta used"
                                        ::= {apStaOnOffLineStat 8}
	onLineTime                          OBJECT-TYPE SYNTAX Unsigned32
                                        MAX-ACCESS  read-only   STATUS current 
                                        DESCRIPTION "sta on line time"
                                        ::= {apStaOnOffLineStat 9}
	offLineTime                         OBJECT-TYPE SYNTAX Unsigned32
                                        MAX-ACCESS  read-only   STATUS current 
                                        DESCRIPTION "sta off line time"
                                        ::= {apStaOnOffLineStat 10}
	innerIPAddr                         OBJECT-TYPE SYNTAX IpAddress
                                        MAX-ACCESS  read-only   STATUS current 
                                        DESCRIPTION "IP address for inside network"
                                        ::= {apStaOnOffLineStat 11}
	outerSrcIPv4                        OBJECT-TYPE SYNTAX IpAddress
                                        MAX-ACCESS  read-only   STATUS current 
                                        DESCRIPTION "IP address for outside network"
                                        ::= {apStaOnOffLineStat 12}
	outerSrcIPv6                        OBJECT-TYPE SYNTAX IpAddress
                                        MAX-ACCESS  read-only   STATUS current 
                                        DESCRIPTION "IPv6 address for outside network"
                                        ::= {apStaOnOffLineStat 13}
	outerSrcIPv4PortStart               OBJECT-TYPE SYNTAX Unsigned32
                                        MAX-ACCESS  read-only   STATUS current 
                                        DESCRIPTION "the start IPv4-port for outside network"
                                        ::= {apStaOnOffLineStat 14}
	outerSrcIPv4PortEnd                 OBJECT-TYPE SYNTAX Unsigned32
                                        MAX-ACCESS  read-only   STATUS current 
                                        DESCRIPTION "the end IPv4-port for outside network"
                                        ::= {apStaOnOffLineStat 15}
    outerSrcIPv6PortStart               OBJECT-TYPE SYNTAX Unsigned32
                                        MAX-ACCESS  read-only   STATUS current 
                                        DESCRIPTION "the start IPv6-port for outside network"
                                        ::= {apStaOnOffLineStat 16}
    outerSrcIPv6PortEnd                 OBJECT-TYPE SYNTAX Unsigned32
                                        MAX-ACCESS  read-only   STATUS current 
                                        DESCRIPTION "the end IPv6-port for outside network"
                                        ::= {apStaOnOffLineStat 17}
	staMac                              OBJECT-TYPE SYNTAX MacAddress
                                        MAX-ACCESS  read-only   STATUS current 
                                        DESCRIPTION "MAC for sta"
                                        ::= {apStaOnOffLineStat 18}
	devMac                               OBJECT-TYPE SYNTAX MacAddress
                                        MAX-ACCESS  read-only   STATUS current 
                                        DESCRIPTION "MAC for AP"
                                        ::= {apStaOnOffLineStat 19}
	devLongitude                         OBJECT-TYPE SYNTAX DisplayString
                                        MAX-ACCESS  read-only   STATUS current 
                                        DESCRIPTION "longitude for AP"
                                        ::= {apStaOnOffLineStat 20}
	devLatitude                          OBJECT-TYPE SYNTAX DisplayString
                                        MAX-ACCESS  read-only   STATUS current 
                                        DESCRIPTION "latitude for AP"
                                        ::= {apStaOnOffLineStat 21}
	terminalFieldStrength               OBJECT-TYPE SYNTAX DisplayString
                                        MAX-ACCESS  read-only   STATUS current 
                                        DESCRIPTION "terminal field strength"
                                        ::= {apStaOnOffLineStat 22}
	xCoordinate                         OBJECT-TYPE SYNTAX DisplayString
                                        MAX-ACCESS  read-only   STATUS current 
                                        DESCRIPTION "X coordinate"
                                        ::= {apStaOnOffLineStat 23}
	yCoordinate                         OBJECT-TYPE SYNTAX DisplayString
                                        MAX-ACCESS  read-only   STATUS current 
                                        DESCRIPTION "Y coordinate"
                                        ::= {apStaOnOffLineStat 24}
	staName                             OBJECT-TYPE SYNTAX DisplayString
                                        MAX-ACCESS  read-only   STATUS current 
                                        DESCRIPTION "sta name"
                                        ::= {apStaOnOffLineStat 25}
	staIMSI                             OBJECT-TYPE SYNTAX DisplayString
                                        MAX-ACCESS  read-only   STATUS current 
                                        DESCRIPTION "sta IMSI"
                                        ::= {apStaOnOffLineStat 26}
	staIMEI                             OBJECT-TYPE SYNTAX DisplayString
                                        MAX-ACCESS  read-only   STATUS current 
                                        DESCRIPTION "sta IMEI"
                                        ::= {apStaOnOffLineStat 27}
	staOSName                           OBJECT-TYPE SYNTAX DisplayString
                                        MAX-ACCESS  read-only   STATUS current 
                                        DESCRIPTION "sta OS name"
                                        ::= {apStaOnOffLineStat 28}
	staBrand                            OBJECT-TYPE SYNTAX DisplayString
                                        MAX-ACCESS  read-only   STATUS current 
                                        DESCRIPTION "sta brand"
                                        ::= {apStaOnOffLineStat 29}
	staModel                            OBJECT-TYPE SYNTAX DisplayString
                                        MAX-ACCESS  read-only   STATUS current 
                                        DESCRIPTION "sta model"
                                        ::= {apStaOnOffLineStat 30}  
                                        
                                        
                                        
     ------------------------------------------------------------------------------
    ------------------------------------------------------------------------------
      apInfoStringTable         OBJECT-TYPE
        SYNTAX                  SEQUENCE OF ApInfoStringEntry
        MAX-ACCESS              not-accessible
        STATUS                  current
        DESCRIPTION             ""
        ::= {apStat       126}

        apInfoStringEntry                  OBJECT-TYPE
            SYNTAX                  ApInfoStringEntry
            MAX-ACCESS              not-accessible
            STATUS                  current
            DESCRIPTION             ""
            INDEX                   {apInfoStringNo}
            ::= {apInfoStringTable      1}

        ApInfoStringEntry  ::= SEQUENCE
        {           
        	apInfoStringNo                    Unsigned32,
            apInfoStringList					DisplayString
        }
         apInfoStringNo		                	OBJECT-TYPE SYNTAX Unsigned32
                                            MAX-ACCESS  read-only   STATUS current 
                                           DESCRIPTION "Ap List Num"
                                            ::= {apInfoStringEntry 1}
         apInfoStringList                          OBJECT-TYPE SYNTAX DisplayString
                                            MAX-ACCESS  read-only   STATUS current 
                                            DESCRIPTION "apInfo String List"
                                            ::= {apInfoStringEntry 2}                                     
                                        
                                        
                                        
                                        
                                        
                                        
     
    ----------------------------------------------------------------------------
    -- apOper
    ----------------------------------------------------------------------------
    apOper                                  OBJECT IDENTIFIER ::= {gbcom 14}
    ----------------------------------------------------------------------------
    -- apSysOper
    ----------------------------------------------------------------------------
    apSysOper                               OBJECT IDENTIFIER ::= {apOper 1} 
    
    	
        apSoftwareUpdate                    OBJECT-TYPE SYNTAX Integer32{normal(0), update(1)}    
                                            MAX-ACCESS  read-write   STATUS current 
                                            DESCRIPTION "ap software update"
                                            ::= {apSysOper 1} 
        apSysRestart                        OBJECT-TYPE SYNTAX Integer32{normal(0), restart(1)}    
                                            MAX-ACCESS  read-write   STATUS current 
                                            DESCRIPTION "ap system restart"
                                            ::= {apSysOper 2}
        apSysReset                        	OBJECT-TYPE SYNTAX Integer32{normal(0), reset(1)}    
                                            MAX-ACCESS  read-write   STATUS current 
                                            DESCRIPTION "ap system reset"
                                            ::= {apSysOper 3}
        apCfgDataFileImpExp                 OBJECT-TYPE SYNTAX Integer32{normal(0), import(1), export(2)}    
                                            MAX-ACCESS  read-write   STATUS current 
                                            DESCRIPTION "ap config data file import/export"
                                            ::= {apSysOper 4}
        apDiagnoseFile                      OBJECT-TYPE SYNTAX Integer32{normal(0), export(1)}    
                                            MAX-ACCESS  read-write   STATUS current 
                                            DESCRIPTION "ap diagnose file"
                                            ::= {apSysOper 5}
        sysStopRecover                      OBJECT-TYPE SYNTAX Integer32{normal(0), stop(1), recover(2)}    
                                            MAX-ACCESS  read-write   STATUS current 
                                            DESCRIPTION ""
                                            ::= {apSysOper 6}  
                                            
                                        
        sendOfflineConfigFile               OBJECT-TYPE SYNTAX DisplayString    
                                            MAX-ACCESS  read-write   STATUS current 
                                            DESCRIPTION "ap send offline file"
                                            ::= {apSysOper 7} 
                                                
                                                                                                               
    ----------------------------------------------------------------------------
    -- apFileTransConfig
    ----------------------------------------------------------------------------
    apFileTransConfig                       OBJECT IDENTIFIER ::= {apOper 2} 
    

        loadFlag                            OBJECT-TYPE SYNTAX Integer32{download(1),upload(2)}
                                            MAX-ACCESS  read-write   STATUS current 
                                            DESCRIPTION "load flag"
                                            DEFVAL {1}
                                            ::= {apFileTransConfig 1}
        fileName                            OBJECT-TYPE SYNTAX DisplayString
                                            MAX-ACCESS  read-write   STATUS current 
                                            DESCRIPTION "file name"
                                            ::= {apFileTransConfig 2}
        fileType                            OBJECT-TYPE SYNTAX Integer32{software(1),config(2),diagnose(3),other(4)}
                                            MAX-ACCESS  read-write   STATUS current 
                                            DESCRIPTION "file type"
                                            DEFVAL {1}
                                            ::= {apFileTransConfig 3}
        transProtocol                       OBJECT-TYPE SYNTAX Integer32{ftp(1),tftp(2),http(3),https(4)}
                                            MAX-ACCESS  read-write   STATUS current 
                                            DESCRIPTION "trans protocol"
                                            DEFVAL {1}
                                            ::= {apFileTransConfig 4}
        serverAddr                          OBJECT-TYPE SYNTAX IpAddress
                                            MAX-ACCESS  read-write   STATUS current 
                                            DESCRIPTION "server address"
                                            ::= {apFileTransConfig 5}
        serverPort                          OBJECT-TYPE SYNTAX Integer32
                                            MAX-ACCESS  read-write   STATUS current 
                                            DESCRIPTION "server port"
                                            ::= {apFileTransConfig 6}
        serverUserName                      OBJECT-TYPE SYNTAX DisplayString
                                            MAX-ACCESS  read-write   STATUS current 
                                            DESCRIPTION "server user name"
                                            ::= {apFileTransConfig 7}
        serverPasswd                        OBJECT-TYPE SYNTAX DisplayString
                                            MAX-ACCESS  read-write   STATUS current 
                                            DESCRIPTION "server password"
                                            ::= {apFileTransConfig 8}
        transStatus                         OBJECT-TYPE SYNTAX Integer32{success(1),get-file-fail(2),file-wrong(3),flash-error(4)}
                                            MAX-ACCESS  read-only   STATUS current 
                                            DESCRIPTION "transfer status"
                                            ::= {apFileTransConfig 9}
        failReason                          OBJECT-TYPE SYNTAX DisplayString
                                            MAX-ACCESS  read-only   STATUS current 
                                            DESCRIPTION "fail reason"
                                            ::= {apFileTransConfig 10}
        fileVersion                         OBJECT-TYPE SYNTAX DisplayString
                                            MAX-ACCESS  read-write   STATUS current 
                                            DESCRIPTION "file version"
                                            ::= {apFileTransConfig 11}
    ----------------------------------------------------------------------------
    -- gwApOper
    ----------------------------------------------------------------------------
    gwApOper                               OBJECT IDENTIFIER ::= {apOper 3} 
    
    	
        apOperAction                    	OBJECT-TYPE SYNTAX Integer32{reboot(1), upgrade(2), update(3), ssidcfg(4)}    
                                            MAX-ACCESS  read-write   STATUS current 
                                            DESCRIPTION " "
                                            ::= {gwApOper 1} 
        apOperMac                        	OBJECT-TYPE SYNTAX DisplayString    
                                            MAX-ACCESS  read-write   STATUS current 
                                            DESCRIPTION " "
                                            ::= {gwApOper 2} 
        apCfgFirstSsid                      OBJECT-TYPE SYNTAX DisplayString    
                                            MAX-ACCESS  read-write   STATUS current 
                                            DESCRIPTION " "
                                            ::= {gwApOper 3}
        apCfgSecondSsid                     OBJECT-TYPE SYNTAX DisplayString    
                                            MAX-ACCESS  read-write   STATUS current 
                                            DESCRIPTION " "
                                            ::= {gwApOper 4}
        apTotalLink                         OBJECT-TYPE SYNTAX Integer32    
                                            MAX-ACCESS  read-write   STATUS current 
                                            DESCRIPTION " "
                                            ::= {gwApOper 5}
        apRoad                              OBJECT-TYPE SYNTAX Integer32    
                                            MAX-ACCESS  read-write   STATUS current 
                                            DESCRIPTION " "
                                            ::= {gwApOper 6}
        apCfgMemo                           OBJECT-TYPE SYNTAX DisplayString    
                                            MAX-ACCESS  read-write   STATUS current 
                                            DESCRIPTION " "
                                            ::= {gwApOper 7}
        apSsids                             OBJECT-TYPE SYNTAX DisplayString    
                                            MAX-ACCESS  read-write   STATUS current 
                                            DESCRIPTION " "
                                            ::= {gwApOper 8}             

    ----------------------------------------------------------------------------
    -- gwApBasicConfig
    ----------------------------------------------------------------------------
    gwApBasicConfig                         OBJECT IDENTIFIER ::= {apOper 4} 
    
    	
        radioCommit                    	    OBJECT-TYPE SYNTAX Integer32{normal(0), commit(1)}    
                                            MAX-ACCESS  read-write   STATUS current 
                                            DESCRIPTION " "
                                            ::= {gwApBasicConfig 1} 
        radioApMac                        	OBJECT-TYPE SYNTAX DisplayString    
                                            MAX-ACCESS  read-write   STATUS current 
                                            DESCRIPTION " "
                                            ::= {gwApBasicConfig 2} 
        radioMode1                      	OBJECT-TYPE SYNTAX Integer32{dot11b(2),dot11g(3),dot11bg(6),dot11gn(16),dot11g-gn(20),dot11bgn(22)}    
                                            MAX-ACCESS  read-write   STATUS current 
                                            DESCRIPTION " "
                                            ::= {gwApBasicConfig 3}
        radioMode2                     		OBJECT-TYPE SYNTAX Integer32{dot11a(1),dot11an(8),dot11a-an(9)}    
                                            MAX-ACCESS  read-write   STATUS current 
                                            DESCRIPTION " "
                                            ::= {gwApBasicConfig 4}
        channel1                         	OBJECT-TYPE SYNTAX Integer32    
                                            MAX-ACCESS  read-write   STATUS current 
                                            DESCRIPTION " "
                                            ::= {gwApBasicConfig 5}
        channel2                            OBJECT-TYPE SYNTAX Integer32    
                                            MAX-ACCESS  read-write   STATUS current 
                                            DESCRIPTION " "
                                            ::= {gwApBasicConfig 6}
        maxpower1                           OBJECT-TYPE SYNTAX Integer32    
                                            MAX-ACCESS  read-write   STATUS current 
                                            DESCRIPTION " "
                                            ::= {gwApBasicConfig 7}
        maxpower2                           OBJECT-TYPE SYNTAX Integer32    
                                            MAX-ACCESS  read-write   STATUS current 
                                            DESCRIPTION " "
                                            ::= {gwApBasicConfig 8}
        wifiStatus1                         OBJECT-TYPE SYNTAX Integer32{off(0), on(1)}    
                                            MAX-ACCESS  read-write   STATUS current 
                                            DESCRIPTION " "
                                            ::= {gwApBasicConfig 9}
        wifiStatus2                         OBJECT-TYPE SYNTAX Integer32{off(0), on(1)}    
                                            MAX-ACCESS  read-write   STATUS current 
                                            DESCRIPTION " "
                                            ::= {gwApBasicConfig 10}
        natEnable                           OBJECT-TYPE SYNTAX Integer32{off(0), on(1)}    
                                            MAX-ACCESS  read-write   STATUS current 
                                            DESCRIPTION " "
                                            ::= {gwApBasicConfig 11}
        antiFish                            OBJECT-TYPE SYNTAX Integer32{off(0), on(1)}    
                                            MAX-ACCESS  read-write   STATUS current 
                                            DESCRIPTION " "
                                            ::= {gwApBasicConfig 12}              
        monitorEnable                       OBJECT-TYPE SYNTAX Integer32{off(0), on(1)}    
                                            MAX-ACCESS  read-write   STATUS current 
                                            DESCRIPTION " "
                                            ::= {gwApBasicConfig 13}
        monitorPeriod                       OBJECT-TYPE SYNTAX Integer32 UNITS "second"    
                                            MAX-ACCESS  read-write   STATUS current 
                                            DESCRIPTION " "
                                            ::= {gwApBasicConfig 14}
                                            
    ----------------------------------------------------------------------------
    -- gwApSsidConfig
    ----------------------------------------------------------------------------
    gwApSsidConfig                         	OBJECT IDENTIFIER ::= {apOper 5} 
    
    	
        ssidCommit                    	    OBJECT-TYPE SYNTAX Integer32{normal(0), commit(1)}    
                                            MAX-ACCESS  read-write   STATUS current 
                                            DESCRIPTION " "
                                            ::= {gwApSsidConfig 1} 
		ssidApMac                           OBJECT-TYPE SYNTAX DisplayString    
                                            MAX-ACCESS  read-write   STATUS current 
                                            DESCRIPTION " "
                                            ::= {gwApSsidConfig 2}
        ssidVlan                        	OBJECT-TYPE SYNTAX Integer32    
                                            MAX-ACCESS  read-write   STATUS current 
                                            DESCRIPTION " "
                                            ::= {gwApSsidConfig 3} 
        oldSsidName                      	OBJECT-TYPE SYNTAX DisplayString    
                                            MAX-ACCESS  read-write   STATUS current 
                                            DESCRIPTION " "
                                            ::= {gwApSsidConfig 4}
        newSsidName                     	OBJECT-TYPE SYNTAX DisplayString    
                                            MAX-ACCESS  read-write   STATUS current 
                                            DESCRIPTION " "
                                            ::= {gwApSsidConfig 5}
        ssidEnable                         	OBJECT-TYPE SYNTAX Integer32{off(0), on(1)}    
                                            MAX-ACCESS  read-write   STATUS current 
                                            DESCRIPTION " "
                                            ::= {gwApSsidConfig 6}
        ssidHidden                          OBJECT-TYPE SYNTAX Integer32{off(0), on(1)}    
                                            MAX-ACCESS  read-write   STATUS current 
                                            DESCRIPTION " "
                                            ::= {gwApSsidConfig 7}
        encryptMode                         OBJECT-TYPE SYNTAX Integer32{open(1),shared(2),wpa-psk(3),wpa2-psk(4),wpapsk-wap2psk(5),wpa(6),wpa2(7),wpa-wap2(8)}    
                                            MAX-ACCESS  read-write   STATUS current 
                                            DESCRIPTION " "
                                            ::= {gwApSsidConfig 8}
        passwd                           	OBJECT-TYPE SYNTAX DisplayString    
                                            MAX-ACCESS  read-write   STATUS current 
                                            DESCRIPTION " "
                                            ::= {gwApSsidConfig 9}
        ssidRadioId                         OBJECT-TYPE SYNTAX Integer32    
                                            MAX-ACCESS  read-write   STATUS current 
                                            DESCRIPTION " "
                                            ::= {gwApSsidConfig 10}           
                                            
    ----------------------------------------------------------------------------
    -- gwApQosConfig
    ----------------------------------------------------------------------------
    gwApQosConfig                         	OBJECT IDENTIFIER ::= {apOper 6} 
    
    	
        qosCommit                    		OBJECT-TYPE SYNTAX Integer32{normal(0), commit(1)}    
                                            MAX-ACCESS  read-write   STATUS current 
                                            DESCRIPTION " "
                                            ::= {gwApQosConfig 1}
        qosApMac                            OBJECT-TYPE SYNTAX DisplayString    
                                            MAX-ACCESS  read-write   STATUS current 
                                            DESCRIPTION " "
                                            ::= {gwApQosConfig 2}         
        qosSsidName                        	OBJECT-TYPE SYNTAX DisplayString    
                                            MAX-ACCESS  read-write   STATUS current 
                                            DESCRIPTION " "
                                            ::= {gwApQosConfig 3} 
        qosUpRate                      		OBJECT-TYPE SYNTAX Integer32 UNITS "kbps"    
                                            MAX-ACCESS  read-write   STATUS current 
                                            DESCRIPTION " "
                                            ::= {gwApQosConfig 4}
        qosDwRate                     		OBJECT-TYPE SYNTAX Integer32 UNITS "kbps"   
                                            MAX-ACCESS  read-write   STATUS current 
                                            DESCRIPTION " "
                                            ::= {gwApQosConfig 5}
        qosSsidRadioId                      OBJECT-TYPE SYNTAX Integer32    
                                            MAX-ACCESS  read-write   STATUS current 
                                            DESCRIPTION " "
                                            ::= {gwApQosConfig 6}       
                                            
                                            
  	gwDevSsidConfig                         	OBJECT IDENTIFIER ::= {apOper 7} 
    
    	
        DevSsidOperType                    	OBJECT-TYPE SYNTAX Integer32{normal(0), commit(1)}    
                                            MAX-ACCESS  read-write   STATUS current 
                                            DESCRIPTION "1:add 2:modify 3:del"
                                            ::= {gwDevSsidConfig 1} 
		DevSsidBssid                           OBJECT-TYPE SYNTAX DisplayString    
                                            MAX-ACCESS  read-write   STATUS current 
                                            DESCRIPTION " "
                                            ::= {gwDevSsidConfig 2}
        DevSsidName                     	OBJECT-TYPE SYNTAX DisplayString    
                                            MAX-ACCESS  read-write   STATUS current 
                                            DESCRIPTION "ssid name"
                                            ::= {gwDevSsidConfig 3}
        DevSsidRadioId                         OBJECT-TYPE SYNTAX Integer32    
                                            MAX-ACCESS  read-write   STATUS current 
                                            DESCRIPTION "2.4G==1 5G==2"
                                            ::= {gwDevSsidConfig 4}           
                                            
       
	
END
